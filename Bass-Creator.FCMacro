import FreeCAD as App
import Part
import importSVG
import os
import Draft
import math
import gc

doc = App.activeDocument()
if not doc:
    doc = App.newDocument("SwainyBass_Assembly")

existing_objects = set(doc.Objects)

# ==========================================
# --- 0. PREFERENCES & CONFIGURATION -------
# ==========================================
draft_prefs = App.ParamGet("User parameter:BaseApp/Preferences/Mod/Draft")
draft_prefs.SetFloat("importSVGScale", 1.0)        # Force 1:1 scale
draft_prefs.SetFloat("svgDiscretization", 0.05)    # Smooth curve discretization

is_left_handed = True  
side_multiplier = -1 if is_left_handed else 1

# Optional Hardware Features
include_gk_channel = True  # Set to True to generate internal GK-3 wire tube passage

# Carbon Fiber wrap allowance (in mm)
cf_wrap_thickness = 0.0  # Set to 0.0 for un-shrunk single-piece core with truss/CF rods & logo

# 3D Printing Fit Clearance Offset (0.25mm per side = 0.5mm overall clearance)
print_clearance = 0.25 

# Enable full-length continuous carbon fiber tube tunnels for 3D printed cores
is_3d_printed_core = True  
cf_tube_od = 6.0    # Outer diameter of carbon fiber reinforcement tubes (mm)
cf_tube_clearance = 0.20  # Print clearance allowance (0.1mm radial)

FILES = {
    "body_contour": "/home/dan/Downloads/swainybass-2026-07-body.svg",
    "headstock": "/home/dan/Downloads/swainybass-2026-06-headstock-complete.svg",
    "cavity": "/home/dan/Downloads/swainybass-2026-06-cavity.svg",
    "cavity_flange": "/home/dan/Downloads/swainybass-2026-06-cavityflange.svg",
    "pot_holes": "/home/dan/Downloads/swainybass-2026-06-through-holes.svg",
    "logo": "/home/dan/Downloads/swainybass-logo.svg"
}

scale_length = 864.0
epsilon = 0.005 

# Core reference landmarks
span_end_x = scale_length
neck_length = (0.75 * scale_length) + 5.0  # 653.0 mm
neck_stop_x = span_end_x - neck_length     # 211.0 mm (Heel interface)

controls_y = -100.0 * side_multiplier

# M5 Body-to-Core Attachment Screw Landmarks (X = 165mm clears belly scoop)
m5_screw_x_coords = [10.0, 165.0]
m5_screw_y_coords = [-25.0, 25.0]

# --- 0.1 RELIEF CALCULATOR FOR FRETBOARD FORWARD BOW ---
def get_fretboard_relief_dip(x):
    """Calculates 0.3mm parabolic forward-bow relief dip along playing length if CF wrap is enabled."""
    if cf_wrap_thickness > 0.0:
        t = (x - neck_stop_x) / (span_end_x - neck_stop_x)
        t = max(0.0, min(1.0, t))
        return 0.30 * 4.0 * t * (1.0 - t)
    return 0.0

# ==========================================
# --- 1. GEOMETRY HELPER FUNCTIONS ---------
# ==========================================

def get_circle_properties(shape):
    for edge in shape.Edges:
        try:
            curve = edge.Curve
            if hasattr(curve, "Center") and hasattr(curve, "Radius"):
                curve_name = type(curve).__name__
                if "Circle" in curve_name or "ArcOfCircle" in curve_name:
                    return curve.Radius, curve.Center
        except Exception:
            pass
    bbox = shape.BoundBox
    cx = (bbox.XMax + bbox.XMin) / 2.0
    cy = (bbox.YMax + bbox.YMin) / 2.0
    rx = (bbox.XMax - bbox.XMin) / 2.0
    ry = (bbox.YMax - bbox.YMin) / 2.0
    return (rx + ry) / 2.0, App.Vector(cx, cy, bbox.Center.z)


def create_svg_solid(filepath, thickness, name, doc, offset_amount=0.0):
    if not os.path.exists(filepath):
        App.Console.PrintWarning(f"File not found at {filepath}\n")
        return None

    old_objs = set(doc.Objects)
    try:
        importSVG.insert(filepath, doc.Name)
        doc.recompute()
    except Exception as e:
        App.Console.PrintError(f"Failed to import {name} SVG: {str(e)}\n")
        return None
    
    new_objs = [obj for doc_obj in [doc] for obj in doc_obj.Objects if obj not in old_objs]
    if not new_objs:
        return None

    in_memory_shape = None
    try:
        if hasattr(Draft, "make_sketch"):
            sketch = Draft.make_sketch(new_objs, autoconstraints=True)
        else:
            sketch = Draft.makeSketch(new_objs, autoconstraints=True)
            
        doc.recompute()
        
        extrude = doc.addObject("Part::Extrusion", "TempExtrude")
        extrude.Base = sketch
        extrude.Dir = App.Vector(0, 0, thickness)
        extrude.Solid = True
        doc.recompute()
        
        in_memory_shape = extrude.Shape.copy()

        if abs(offset_amount) > 0.001 and in_memory_shape:
            try:
                face = in_memory_shape.Faces[0]
                wire = face.OuterWire
                shrunk_wire = wire.makeOffset2D(-offset_amount)
                shrunk_face = Part.Face(shrunk_wire)
                in_memory_shape = shrunk_face.extrude(App.Vector(0, 0, thickness))
            except Exception as offset_err:
                App.Console.PrintWarning(f"SVG 2D offset failed for {name}: {str(offset_err)}\n")

    except Exception as e:
        App.Console.PrintError(f"Failed to build solid for {name}: {str(e)}\n")

    all_new = [obj for doc_obj in [doc] for obj in doc_obj.Objects if obj not in old_objs]
    for obj in all_new:
        try: doc.removeObject(obj.Name)
        except Exception: pass
    doc.recompute()
    
    return in_memory_shape


def create_semi_ellipse_wire(x, y_center, width, thickness, z_top=17.0):
    ry = width / 2.0
    rz = thickness
    num_points = 12 
    arc_points = []
    for i in range(num_points + 1):
        theta = math.pi + (i / float(num_points)) * math.pi
        curr_y = y_center + ry * math.cos(theta)
        curr_z = z_top + rz * math.sin(theta)
        arc_points.append(App.Vector(x, curr_y, curr_z))
    
    try:
        curve = Part.BSplineCurve()
        curve.interpolate(arc_points)
        curve_edge = curve.toShape()
        flat_edge = Part.makeLine(arc_points[-1], arc_points[0])
        return Part.Wire([curve_edge, flat_edge])
    except Exception:
        polygon_points = arc_points + [arc_points[0]]
        return Part.makePolygon(polygon_points)


def create_asymmetric_rectangle_wire(x, y_min, y_max, thickness, z_top=17.0):
    p1 = App.Vector(x, y_min, z_top)          
    p2 = App.Vector(x, y_min, z_top - thickness)     
    p3 = App.Vector(x, y_max, z_top - thickness)     
    p4 = App.Vector(x, y_max, z_top)          
    return Part.makePolygon([p1, p2, p3, p4, p1])


def create_fretboard_radiused_wire(x, y_center, width, thickness=7.0, z_bottom=17.0, radius=500.0):
    """Creates a crowned profile wire for the fretboard taking local parabolic relief into account."""
    dip = get_fretboard_relief_dip(x)
    actual_thickness = thickness - dip
    
    ry = width / 2.0
    z_peak = z_bottom + actual_thickness
    z_center_circle = z_peak - radius
    
    z_edge = z_center_circle + math.sqrt(radius**2 - ry**2)
    
    p_start = App.Vector(x, y_center - ry, z_edge)
    p_mid = App.Vector(x, y_center, z_peak)
    p_end = App.Vector(x, y_center + ry, z_edge)
    
    p_bot_right = App.Vector(x, y_center + ry, z_bottom)
    p_bot_left = App.Vector(x, y_center - ry, z_bottom)
    
    arc = Part.Arc(p_start, p_mid, p_end)
    arc_edge = arc.toShape()
    
    edge_right = Part.makeLine(p_end, p_bot_right)
    edge_bottom = Part.makeLine(p_bot_right, p_bot_left)
    edge_left = Part.makeLine(p_bot_left, p_start)
    
    wire = Part.Wire([arc_edge, edge_right, edge_bottom, edge_left])
    return wire


def create_curved_slot_cutter(x, y_center, width, slot_width=0.6, slot_depth=1.5, radius=500.0):
    """Generates a concentric curved cylinder solid aligned with local fretboard relief height."""
    dip = get_fretboard_relief_dip(x)
    z_peak_fret = (17.0 + 7.0) - dip  # Local peak surface height
    
    ry = (width + 10.0) / 2.0
    z_center_circle = z_peak_fret - radius
    
    r_top = radius + 1.0  
    r_bot = radius - slot_depth  
    
    z_top_edge = z_center_circle + math.sqrt(r_top**2 - ry**2)
    z_bot_edge = z_center_circle + math.sqrt(r_bot**2 - ry**2)
    
    p_top_start = App.Vector(x, y_center - ry, z_top_edge)
    p_top_mid = App.Vector(x, y_center, z_center_circle + r_top)
    p_top_end = App.Vector(x, y_center + ry, z_top_edge)
    
    p_bot_start = App.Vector(x, y_center - ry, z_bot_edge)
    p_bot_mid = App.Vector(x, y_center, z_center_circle + r_bot)
    p_bot_end = App.Vector(x, y_center + ry, z_bot_edge)
    
    arc_top = Part.Arc(p_top_start, p_top_mid, p_top_end).toShape()
    arc_bot = Part.Arc(p_bot_end, p_bot_mid, p_bot_start).toShape()
    
    edge_right = Part.makeLine(p_top_end, p_bot_end)
    edge_left = Part.makeLine(p_bot_start, p_top_start)
    
    wire = Part.Wire([arc_top, edge_right, arc_bot, edge_left])
    face = Part.Face(wire)
    solid = face.extrude(App.Vector(slot_width, 0, 0))
    solid.translate(App.Vector(-slot_width / 2.0, 0, 0))
    return solid


def create_ramp_wire(x, y_center, width, thickness=8.0, z_bottom=11.0, radius=500.0):
    """Creates a crowned profile wire for the finger ramp using a 500mm radius."""
    ry = width / 2.0
    z_peak = z_bottom + thickness
    z_center_circle = z_peak - radius
    
    z_edge = z_center_circle + math.sqrt(radius**2 - ry**2)
    
    p_start = App.Vector(x, y_center - ry, z_edge)
    p_mid = App.Vector(x, y_center, z_peak)
    p_end = App.Vector(x, y_center + ry, z_edge)
    
    p_bot_right = App.Vector(x, y_center + ry, z_bottom)
    p_bot_left = App.Vector(x, y_center - ry, z_bottom)
    
    arc = Part.Arc(p_start, p_mid, p_end)
    arc_edge = arc.toShape()
    
    edge_right = Part.makeLine(p_end, p_bot_right)
    edge_bottom = Part.makeLine(p_bot_right, p_bot_left)
    edge_left = Part.makeLine(p_bot_left, p_start)
    
    wire = Part.Wire([arc_edge, edge_right, edge_bottom, edge_left])
    return wire


# ==========================================
# --- 2. IMPORT & SECTION HEADSTOCK SVG ----
# ==========================================
headstock_svg_face = None
tuner_cutters = []
outer_wire = None

try:
    importSVG.insert(FILES["headstock"], doc.Name)
    doc.recompute() 
except Exception as e:
    App.Console.PrintError(f"Failed to import Headstock SVG: {str(e)}\n") 

new_objects = [obj for doc_obj in [doc] for obj in doc_obj.Objects if obj not in existing_objects] 
svg_geometry = [obj for obj in new_objects if hasattr(obj, 'Shape') and not obj.Shape.isNull()] 

headstock_top_y = 30.0   
headstock_bottom_y = -30.0 

if svg_geometry:
    headstock_contour = None
    tuner_holes = []
    max_hs_area = 0.0

    for obj in svg_geometry:
        if hasattr(obj, "Shape") and not obj.Shape.isNull():
            bbox = obj.Shape.BoundBox
            area = (bbox.XMax - bbox.XMin) * (bbox.YMax - bbox.YMin)
            if area > max_hs_area:
                if headstock_contour:
                    tuner_holes.append(headstock_contour)
                max_hs_area = area
                headstock_contour = obj
            else:
                tuner_holes.append(obj)

    if headstock_contour:
        hs_outer_shape = headstock_contour.Shape.copy()
        bounds = hs_outer_shape.BoundBox 
        
        target_x = scale_length - bounds.XMin 
        target_y = 0.0 - bounds.Center.y
        hs_outer_shape.translate(App.Vector(target_x, target_y, 0))

        outer_wire = hs_outer_shape.OuterWire if hasattr(hs_outer_shape, "OuterWire") and hs_outer_shape.OuterWire else hs_outer_shape.Wires[0]
        headstock_svg_face = Part.Face(outer_wire)
        
        nut_y_coords = [v.Point.y for v in headstock_svg_face.Vertexes if abs(v.Point.x - scale_length) < 2.0]
        if nut_y_coords:
            headstock_top_y = max(nut_y_coords)
            headstock_bottom_y = min(nut_y_coords)

        for hole_obj in tuner_holes:
            try:
                r, center = get_circle_properties(hole_obj.Shape)
                cyl = Part.makeCylinder(r, 40.0, App.Vector(center.x + target_x, center.y + target_y, -10.0), App.Vector(0, 0, 1))
                tuner_cutters.append(cyl)
            except Exception:
                pass

    for obj in svg_geometry:
        try: doc.removeObject(obj.Name)
        except Exception: pass

width_headstock_nut = headstock_top_y - headstock_bottom_y
center_y = (headstock_top_y + headstock_bottom_y) / 2.0


# ==========================================
# --- 3. BUILD STRUCTURAL CORE -------------
# ==========================================

bridge_start_x = -30.0
bridge_end_x = neck_stop_x  # X = 211.0mm

bridge_core_width = 110.0
bridge_core_height = 30.0  

# Z Reference Planes (Full-Scale Baseline)
z_neck_top = 17.0
cap_thickness = 4.0
z_step_interface = z_neck_top - cap_thickness  # Z = 13.0mm
z_bridge_bottom = z_step_interface - bridge_core_height  # Z = -17.0mm

width_heel = 90.0 
thickness_heel = 24.5  

# Wire profile for neck heel joint
wire_neck_heel_full = create_semi_ellipse_wire(neck_stop_x, center_y, width_heel, thickness_heel, z_top=z_neck_top)

# --- 3.1 VERTICAL-WALL TRANSITION (FULL SCALE) ---
bridge_block_solid = None
try:
    taper_start_x = bridge_start_x + 80.0  # X = 50.0mm
    
    bridge_block_solid = Part.makeBox(
        bridge_end_x - bridge_start_x, 
        bridge_core_width, 
        bridge_core_height, 
        App.Vector(bridge_start_x, -bridge_core_width / 2.0, z_bridge_bottom)
    )
    
    y_full = bridge_core_width / 2.0      
    y_heel = width_heel / 2.0             
    
    poly_top = Part.makePolygon([
        App.Vector(taper_start_x, y_full, z_bridge_bottom - 2.0),
        App.Vector(neck_stop_x + 5.0, y_full, z_bridge_bottom - 2.0),
        App.Vector(neck_stop_x + 5.0, y_heel, z_bridge_bottom - 2.0),
        App.Vector(taper_start_x, y_full, z_bridge_bottom - 2.0)
    ])
    cutter_top = Part.Face(poly_top).extrude(App.Vector(0, 0, bridge_core_height + 10.0))
    
    poly_bot = Part.makePolygon([
        App.Vector(taper_start_x, -y_full, z_bridge_bottom - 2.0),
        App.Vector(neck_stop_x + 5.0, -y_full, z_bridge_bottom - 2.0),
        App.Vector(neck_stop_x + 5.0, -y_heel, z_bridge_bottom - 2.0),
        App.Vector(taper_start_x, -y_full, z_bridge_bottom - 2.0)
    ])
    cutter_bot = Part.Face(poly_bot).extrude(App.Vector(0, 0, bridge_core_height + 10.0))
    
    bridge_block_solid = bridge_block_solid.cut(Part.makeCompound([cutter_top, cutter_bot]))

    # Apply relief filleting to full-scale bridge block
    bridge_relief_edges = []
    for edge in bridge_block_solid.Edges:
        bbox = edge.BoundBox
        is_bottom_edge = abs(bbox.ZMin - z_bridge_bottom) < 0.1 and abs(bbox.ZMax - z_bridge_bottom) < 0.1
        is_vertical_corner = abs(bbox.ZMax - bbox.ZMin) > (bridge_core_height - 1.0) and (bbox.XMin < (bridge_start_x + 2.0) or abs(bbox.XMax - neck_stop_x) < 2.0)
        if is_bottom_edge or is_vertical_corner:
            bridge_relief_edges.append(edge)

    if bridge_relief_edges:
        for r_bridge in [3.0, 2.0, 1.0]:
            try:
                temp_bridge = bridge_block_solid.makeFillet(r_bridge, bridge_relief_edges)
                if temp_bridge and temp_bridge.isValid() and temp_bridge.Volume > 0:
                    bridge_block_solid = temp_bridge
                    break
            except Exception:
                pass

except Exception as trans_err:
    App.Console.PrintError(f"Vertical transition build failed: {str(trans_err)}\n")

# --- 3.2 ASYMMETRICALLY MATCHED VOLUTE TRANSITION ---
x_volute_end = span_end_x + 20.0  # X = 884.0mm

wire_nut_ellipse = create_semi_ellipse_wire(span_end_x, center_y, width_headstock_nut, 17.0, z_top=z_neck_top)
neck_playing_solid = Part.makeLoft([wire_neck_heel_full, wire_nut_ellipse], True)

headstock_body = headstock_svg_face.extrude(App.Vector(0, 0, 17.0))
trim_back = Part.makeBox(
    100.0, 300.0, 100.0,
    App.Vector(x_volute_end - 100.0, -150.0, -50.0)
)
headstock_body = headstock_body.cut(trim_back)

y_min_hs = -36.0  
y_max_hs = 36.0

if headstock_body and headstock_body.Vertexes:
    target_vertices_y = [
        v.Point.y for v in headstock_body.Vertexes 
        if abs(v.Point.x - x_volute_end) < 1.0
    ]
    if target_vertices_y:
        y_min_hs = min(target_vertices_y)
        y_max_hs = max(target_vertices_y)

wire_hs_section = create_asymmetric_rectangle_wire(
    x_volute_end, y_min_hs, y_max_hs, 17.0, z_top=z_neck_top
)
volute_transition = Part.makeLoft([wire_nut_ellipse, wire_hs_section], True)

# Full-scale un-cut core blank reference (Used for carving the body shell pocket)
full_scale_core_blank = bridge_block_solid.fuse(neck_playing_solid).fuse(volute_transition).fuse(headstock_body)

try:
    seam_edges = []
    for edge in full_scale_core_blank.Edges:
        bbox = edge.BoundBox
        is_seam_x = abs(bbox.Center.x - span_end_x) < 2.0 or abs(bbox.Center.x - x_volute_end) < 2.0
        if is_seam_x and bbox.ZMax < (z_neck_top - 0.1):
            seam_edges.append(edge)

    if seam_edges:
        for r_fillet in [12.0, 10.0, 8.0, 6.0, 4.0, 2.0]:
            try:
                temp_solid = full_scale_core_blank.makeFillet(r_fillet, seam_edges)
                if temp_solid and temp_solid.isValid() and temp_solid.Volume > 0:
                    full_scale_core_blank = temp_solid
                    break
            except Exception:
                pass
except Exception as seam_err:
    App.Console.PrintWarning(f"Volute seam filleting bypassed: {str(seam_err)}\n")

if tuner_cutters:
    full_scale_core_blank = full_scale_core_blank.cut(Part.makeCompound(tuner_cutters))

# --- 3.3 CONSTRUCT SHRUNK CORE & ISOLATE LOCALIZED BRIDGE INSERT BLOCK ---
bridge_insert_solid = None

if cf_wrap_thickness > 0.0:
    w_heel_s = width_heel - (2.0 * cf_wrap_thickness)
    t_heel_s = thickness_heel - (2.0 * cf_wrap_thickness)
    w_nut_s = width_headstock_nut - (2.0 * cf_wrap_thickness)
    z_top_s = z_neck_top - cf_wrap_thickness

    wire_heel_s = create_semi_ellipse_wire(neck_stop_x, center_y, w_heel_s, t_heel_s, z_top=z_top_s)
    wire_nut_s = create_semi_ellipse_wire(span_end_x, center_y, w_nut_s, 17.0 - cf_wrap_thickness, z_top=z_top_s)
    neck_s_solid = Part.makeLoft([wire_heel_s, wire_nut_s], True)

    w_bridge_s = bridge_core_width - (2.0 * cf_wrap_thickness)
    h_bridge_s = bridge_core_height - (2.0 * cf_wrap_thickness)
    z_bridge_bot_s = z_step_interface - h_bridge_s

    bridge_s_solid = Part.makeBox(
        bridge_end_x - bridge_start_x, w_bridge_s, h_bridge_s,
        App.Vector(bridge_start_x, -w_bridge_s / 2.0, z_bridge_bot_s)
    )

    y_full_s = w_bridge_s / 2.0
    y_heel_s = w_heel_s / 2.0
    
    poly_top_s = Part.makePolygon([
        App.Vector(taper_start_x, y_full_s, z_bridge_bot_s - 2.0),
        App.Vector(neck_stop_x + 5.0, y_full_s, z_bridge_bot_s - 2.0),
        App.Vector(neck_stop_x + 5.0, y_heel_s, z_bridge_bot_s - 2.0),
        App.Vector(taper_start_x, y_full_s, z_bridge_bot_s - 2.0)
    ])
    cutter_top_s = Part.Face(poly_top_s).extrude(App.Vector(0, 0, h_bridge_s + 10.0))

    poly_bot_s = Part.makePolygon([
        App.Vector(taper_start_x, -y_full_s, z_bridge_bot_s - 2.0),
        App.Vector(neck_stop_x + 5.0, -y_full_s, z_bridge_bot_s - 2.0),
        App.Vector(neck_stop_x + 5.0, -y_heel_s, z_bridge_bot_s - 2.0),
        App.Vector(taper_start_x, -y_full_s, z_bridge_bot_s - 2.0)
    ])
    cutter_bot_s = Part.Face(poly_bot_s).extrude(App.Vector(0, 0, h_bridge_s + 10.0))

    bridge_s_solid = bridge_s_solid.cut(Part.makeCompound([cutter_top_s, cutter_bot_s]))

    # Fillet bottom edges of shrunk bridge block to match body pocket radii
    s_bridge_relief_edges = []
    for edge in bridge_s_solid.Edges:
        bbox = edge.BoundBox
        is_bottom_edge = abs(bbox.ZMin - z_bridge_bot_s) < 0.1 and abs(bbox.ZMax - z_bridge_bot_s) < 0.1
        is_vertical_corner = abs(bbox.ZMax - bbox.ZMin) > (h_bridge_s - 1.0) and (bbox.XMin < (bridge_start_x + 2.0) or abs(bbox.XMax - neck_stop_x) < 2.0)
        if is_bottom_edge or is_vertical_corner:
            s_bridge_relief_edges.append(edge)

    if s_bridge_relief_edges:
        for r_s in [3.0, 2.0, 1.0]:
            try:
                temp_b = bridge_s_solid.makeFillet(r_s, s_bridge_relief_edges)
                if temp_b and temp_b.isValid() and temp_b.Volume > 0:
                    bridge_s_solid = temp_b
                    break
            except Exception:
                pass

    hs_body_s = headstock_svg_face.extrude(App.Vector(0, 0, 17.0))
    if outer_wire:
        try:
            hs_offset = outer_wire.makeOffset2D(-cf_wrap_thickness)
            if hs_offset and hs_offset.Edges:
                hs_body_s = Part.Face(hs_offset).extrude(App.Vector(0, 0, 17.0 - (2.0 * cf_wrap_thickness)))
                hs_body_s.translate(App.Vector(0, 0, cf_wrap_thickness))
        except Exception:
            pass

    hs_body_s = hs_body_s.cut(trim_back)
    wire_hs_s = create_asymmetric_rectangle_wire(x_volute_end, y_min_hs + cf_wrap_thickness, y_max_hs - cf_wrap_thickness, 17.0 - cf_wrap_thickness, z_top=z_top_s)
    volute_s = Part.makeLoft([wire_nut_s, wire_hs_s], True)

    shrunk_full_core = bridge_s_solid.fuse(neck_s_solid).fuse(volute_s).fuse(hs_body_s)
    if tuner_cutters:
        shrunk_full_core = shrunk_full_core.cut(Part.makeCompound(tuner_cutters))

    # Split shrunk core at X = 30mm (between X = 15mm bridge screw holes and X = 40mm pickup wire tube)
    x_split_boundary = 30.0
    cutter_insert_zone = Part.makeBox(
        x_split_boundary - bridge_start_x, 200.0, 100.0,
        App.Vector(bridge_start_x, -100.0, -50.0)
    )

    bridge_insert_solid = shrunk_full_core.common(cutter_insert_zone)
    structural_core = shrunk_full_core.cut(cutter_insert_zone)
else:
    structural_core = full_scale_core_blank.copy()

# --- 3.4 APPLY SUBTRACTIVE FEATURES TO CORE AND ISOLATED BRIDGE INSERT BLOCK ---
node_radius = 2.1
hole_depth = 25.0   
x_positions = [-15.0, 15.0]  
y_positions = [-45.0, -27.0, -9.0, 9.0, 27.0, 45.0]  

hole_shapes = [
    Part.makeCylinder(node_radius, hole_depth, App.Vector(x, y, z_step_interface), App.Vector(0, 0, -1))
    for x in x_positions for y in y_positions
]

# M5 Threaded Insert Pilot Holes (X = 10mm falls in BridgeInsertBlock, X = 165mm falls in StructuralCore)
m5_screw_10_cutters = []
m5_screw_165_cutters = []

for mx in m5_screw_x_coords:
    for my in m5_screw_y_coords:
        cyl = Part.makeCylinder(2.1, 12.0, App.Vector(mx, my * side_multiplier, z_bridge_bottom), App.Vector(0, 0, 1))
        if mx < 30.0:
            m5_screw_10_cutters.append(cyl)
        else:
            m5_screw_165_cutters.append(cyl)

if bridge_insert_solid:
    # 1. Drill 12-node hole array and X = 10mm M5 inserts into BridgeInsertBlock
    bridge_insert_solid = bridge_insert_solid.cut(Part.makeCompound(hole_shapes))
    if m5_screw_10_cutters:
        bridge_insert_solid = bridge_insert_solid.cut(Part.makeCompound(m5_screw_10_cutters))
    App.Console.PrintMessage("Applied 12-hole node array and forward M5 inserts to isolated BridgeInsertBlock.\n")

    # 2. Drill X = 165mm M5 inserts into main StructuralCore
    if m5_screw_165_cutters:
        structural_core = structural_core.cut(Part.makeCompound(m5_screw_165_cutters))
else:
    # Single-piece core handling
    structural_core = structural_core.cut(Part.makeCompound(hole_shapes))
    all_m5_cutters = m5_screw_10_cutters + m5_screw_165_cutters
    if all_m5_cutters:
        structural_core = structural_core.cut(Part.makeCompound(all_m5_cutters))

# --- CONDITIONAL REINFORCEMENT & TRUSS ROD CUTTING ---
if cf_wrap_thickness == 0.0:
    # 1. Truss Rod Channel and Pocket Cutters (Always present for relief adjustment)
    truss_rod_cutter = Part.makeBox(
        610.0, 6.35, 11.52, 
        App.Vector(neck_stop_x, center_y - 6.35 / 2.0, z_neck_top - 9.52)
    )

    truss_rod_nut_pocket = Part.makeBox(
        35.5, 10.0, 10.0,
        App.Vector(neck_stop_x, center_y - 10.0 / 2.0, z_neck_top - 10.0)
    )

    access_cutter = Part.makeBox(
        30.0, 10.0, 14.0, 
        App.Vector(neck_stop_x - 30.0, center_y - 10.0 / 2.0, z_neck_top - 12.0)
    )

    reinforcement_cutters = [truss_rod_cutter, truss_rod_nut_pocket, access_cutter]

    # 2. Check if building for 3D Printing or CNC Milling
    if 'is_3d_printed_core' in locals() and is_3d_printed_core:
        # =========================================================================
        # --- CONTINUOUS TAPER-ANGLED CF/STEEL TUBE TUNNELS (STRAIGHT RODS) -------
        # =========================================================================
        cf_tube_od = 8.0          # Uniform OD for rigid straight carbon/steel rods (mm)
        cf_tube_clearance = 0.20  # 0.1mm radial clearance for 3D printing fit
        
        r_tube = (cf_tube_od / 2.0) + (cf_tube_clearance / 2.0)  # 3.1mm radius
        z_tube_center = 8.5  # Keeps top of tube below z_step_interface (Z = 13.0mm)
        
        # Landmarks for angled straight vector
        x_bridge_anchor = -15.0   # Anchor inside bridge block
        x_hs_tip = 930.0          # Continues straight into headstock
        
        # Angled Y-positions following neck taper:
        # Wider at the bridge (Y = ±22mm), narrowing at the nut/headstock (Y = ±11mm)
        y_bridge_offset = 22.0  
        y_hs_offset = 11.0      

        for side in [-1, 1]:  # Left and Right sides
            y_start = y_bridge_offset * side
            y_end = y_hs_offset * side

            p_start = App.Vector(x_bridge_anchor, y_start, z_tube_center)
            p_end = App.Vector(x_hs_tip, y_end, z_tube_center)

            # Direct vector and total length along angled axis
            rod_axis = (p_end - p_start)
            tube_length = rod_axis.Length
            dir_vector = rod_axis.normalize()

            # Single straight cylinder extruded along the angled trajectory
            angled_tube_cyl = Part.makeCylinder(r_tube, tube_length, p_start, dir_vector)
            
            reinforcement_cutters.append(angled_tube_cyl)

        App.Console.PrintMessage(f"Cut continuous TAPER-ANGLED {cf_tube_od}mm Rod Tunnels (X = -15mm to 930mm, Y = ±22mm -> ±11mm).\n")

    else:
        # =========================================================================
        # --- STANDARD RECTANGULAR BLIND CHANNELS (CNC MILLED CORE) ---------------
        # =========================================================================
        cf_rod_length = 625.0  
        cf_rod_width = 3.5
        cf_rod_depth = 9.52 + 0.50  # 10.02mm depth
        cf_y_offset = 15.0  

        cf_channel_left = Part.makeBox(
            cf_rod_length, cf_rod_width, cf_rod_depth,
            App.Vector(215.0, center_y - cf_y_offset - (cf_rod_width / 2.0), z_neck_top - cf_rod_depth)
        )

        cf_channel_right = Part.makeBox(
            cf_rod_length, cf_rod_width, cf_rod_depth,
            App.Vector(215.0, center_y + cf_y_offset - (cf_rod_width / 2.0), z_neck_top - cf_rod_depth)
        )
        reinforcement_cutters.extend([cf_channel_left, cf_channel_right])
        App.Console.PrintMessage("Cut standard rectangular CF channels into un-wrapped Core.\n")

    neck_reinforcement_cutters = Part.makeCompound(reinforcement_cutters)
    structural_core = structural_core.cut(neck_reinforcement_cutters)

else:
    App.Console.PrintMessage("Skipped Truss Rod and CF channels (CF Wrap enabled: core rigid enough).\n")

# --- HEADSTOCK LOGO ENGRAVING & INLAY (ONLY WHEN cf_wrap_thickness == 0.0) ---
if cf_wrap_thickness == 0.0 and "logo" in FILES:
    try:
        logo_depth = 0.5
        
        # 1. Extrude raw SVG geometry for pocket cut (extra thickness for clean cut)
        logo_raw = create_svg_solid(FILES["logo"], logo_depth + 2.0, "HeadstockLogo", doc)
        
        # 2. Extrude exact SVG geometry for inlay solid chip (exact 0.5mm depth)
        logo_inlay = create_svg_solid(FILES["logo"], logo_depth, "HeadstockLogoInlaySolid", doc)

        if logo_raw and logo_inlay:
            bbox_logo = logo_raw.BoundBox
            logo_width_x = bbox_logo.XMax - bbox_logo.XMin
            
            # Position 7.5mm from the tip of the headstock
            hs_tip_x = max(v.Point.x for v in structural_core.Vertexes)
            target_logo_x = (hs_tip_x - 7.5) - logo_width_x
            
            # Sample actual headstock profile boundary Y-limits at target_logo_x
            sample_line = Part.makeLine(
                App.Vector(target_logo_x, -200.0, 17.0),
                App.Vector(target_logo_x, 200.0, 17.0)
            )
            hs_intersection = headstock_body.common(sample_line)
            
            if hs_intersection and hs_intersection.Vertexes:
                y_pts = [v.Point.y for v in hs_intersection.Vertexes]
                hs_y_top = max(y_pts)
                hs_y_bot = min(y_pts)
            else:
                hs_y_top = headstock_top_y
                hs_y_bot = headstock_bottom_y

            # Calculate Y-offset to make d_top (hs_y_top - logo_ymax) == d_bot (logo_ymin - hs_y_bot)
            logo_h_y = bbox_logo.YMax - bbox_logo.YMin
            target_logo_y = (hs_y_top + hs_y_bot) / 2.0 - (logo_h_y / 2.0)
            
            y_shift = target_logo_y - bbox_logo.YMin
            x_shift = target_logo_x - bbox_logo.XMin
            z_shift = (z_neck_top - logo_depth) - bbox_logo.ZMin

            # Translate Cutter Pocket
            logo_raw.translate(App.Vector(x_shift, y_shift, z_shift))

            # Cut 0.5mm deep pocket into Headstock
            structural_core = structural_core.cut(logo_raw)
            App.Console.PrintMessage("Successfully engraved 0.5mm Logo with equalized perimeter margins.\n")

            # Translate direct SVG Inlay Solid chip to exact same location
            logo_inlay.translate(App.Vector(x_shift, y_shift, z_shift))

            logo_feature = doc.addObject("Part::Feature", "HeadstockLogoInlay")
            logo_feature.Shape = logo_inlay
            logo_feature.ViewObject.ShapeColor = (0.10, 0.10, 0.10)  # Black inlay/resin preview
            logo_feature.Label = "HeadstockLogoInlay"
            App.Console.PrintMessage("Successfully generated exact SVG HeadstockLogoInlay solid.\n")

    except Exception as logo_err:
        App.Console.PrintError(f"Failed to process headstock logo: {str(logo_err)}\n")

gk_channel_solid = None
if include_gk_channel:
    try:
        p_start_gk = App.Vector(40.0, 0.0, 15.0)
        pts_gk = [
            p_start_gk,
            App.Vector(40.0, controls_y * 0.05, 5.0),    
            App.Vector(40.0, controls_y * 0.12, -10.0),  
            App.Vector(38.0, controls_y * 0.22, -22.0),  
            App.Vector(30.0, controls_y * 0.45, -22.0),  
            App.Vector(15.0, controls_y * 0.75, -22.0),  
            App.Vector(0.0, controls_y, -22.0)           
        ]
        
        curve_gk = Part.BSplineCurve()
        curve_gk.interpolate(pts_gk)
        path_wire_gk = Part.Wire([curve_gk.toShape()])
        
        initial_dir = (pts_gk[1] - pts_gk[0]).normalize()
        circle_gk = Part.makeCircle(5.0, p_start_gk, initial_dir)  
        circle_face_gk = Part.Face(Part.Wire([circle_gk]))
        
        gk_channel_solid = path_wire_gk.makePipe(circle_face_gk)
        structural_core = structural_core.cut(gk_channel_solid)
        App.Console.PrintMessage("Cut GK-3 pickup wire channel into Structural Core.\n")
    except Exception as gk_core_err:
        App.Console.PrintWarning(f"Core wire tubing cut failed: {str(gk_core_err)}\n")
else:
    App.Console.PrintMessage("Skipped GK-3 pickup wire channel (include_gk_channel = False).\n")

core_feature = doc.addObject("Part::Feature", "StructuralCore")
core_feature.Shape = structural_core
core_feature.ViewObject.ShapeColor = (0.75, 0.60, 0.40)

if bridge_insert_solid:
    bridge_insert_feature = doc.addObject("Part::Feature", "BridgeInsertBlock")
    bridge_insert_feature.Shape = bridge_insert_solid
    bridge_insert_feature.ViewObject.ShapeColor = (0.25, 0.25, 0.28)  # Charcoal/PC-CF look
    bridge_insert_feature.Label = "BridgeInsertBlock"
    App.Console.PrintMessage("Successfully isolated BridgeInsertBlock (X = -30mm to +30mm) with matched bottom filleting.\n")


# ==========================================
# --- 4. IMPORT, ALIGN & BUILD BODY WINGS --
# ==========================================

existing_pre_body = set(doc.Objects)
body_solid_shape = None

try:
    importSVG.insert(FILES["body_contour"], doc.Name)
    doc.recompute()
    body_svg_objects = [obj for doc_obj in [doc] for obj in doc_obj.Objects if obj not in existing_pre_body]

    midline_obj, bridge_align_obj = None, None
    for obj in body_svg_objects:
        name_l = obj.Name.lower()
        if 'midline' in name_l: midline_obj = obj
        elif 'bridge' in name_l: bridge_align_obj = obj

    body_translation = App.Vector(0, 0, 0)
    if midline_obj and bridge_align_obj:
        mid_shape = midline_obj.Shape.copy()
        if hasattr(midline_obj, 'Placement') and midline_obj.Placement: mid_shape.transformShape(midline_obj.Placement.toMatrix())
        
        brg_shape = bridge_align_obj.Shape.copy()
        if hasattr(bridge_align_obj, 'Placement') and bridge_align_obj.Placement: brg_shape.transformShape(bridge_align_obj.Placement.toMatrix())

        midline_y = mid_shape.BoundBox.Center.y
        bridge_x = brg_shape.BoundBox.Center.x
        body_translation = App.Vector(-bridge_x, -midline_y, 0)

    body_contour_obj = None
    max_area = 0.0
    for obj in body_svg_objects:
        if 'midline' in obj.Name.lower() or 'bridge' in obj.Name.lower(): continue
        if hasattr(obj, 'Shape') and not obj.Shape.isNull():
            bbox = obj.Shape.BoundBox
            area = (bbox.XMax - bbox.XMin) * (bbox.YMax - bbox.YMin)
            if area > max_area:
                max_area = area
                body_contour_obj = obj

    if body_contour_obj:
        body_sketch = Draft.make_sketch([body_contour_obj], autoconstraints=True)
        extrude = doc.addObject("Part::Extrusion", "TempBodyExtrude")
        extrude.Base = body_sketch
        extrude.Dir = App.Vector(0, 0, 44.0)
        extrude.Solid = True
        doc.recompute()

        body_solid_shape = extrude.Shape.copy()
        body_solid_shape.translate(body_translation)
        body_solid_shape.translate(App.Vector(0, 0, -31.0))

    for obj in body_svg_objects:
        try: doc.removeObject(obj.Name)
        except Exception: pass
    if 'body_sketch' in locals() and body_sketch: doc.removeObject(body_sketch.Name)
    if 'extrude' in locals() and extrude: doc.removeObject(extrude.Name)

except Exception as e:
    App.Console.PrintError(f"Body Contour Import Error: {str(e)}\n")


# ==========================================
# --- 5. BODY FILLETING & ERGONOMICS -------
# ==========================================

if body_solid_shape and not body_solid_shape.isNull():
    try:
        perimeter_edges = []
        for edge in body_solid_shape.Edges:
            bbox = edge.BoundBox
            is_top = abs(bbox.ZMin - 13.0) < 0.1 and abs(bbox.ZMax - 13.0) < 0.1
            is_bottom = abs(bbox.ZMin - (-31.0)) < 0.1 and abs(bbox.ZMax - (-31.0)) < 0.1
            if is_top or is_bottom:
                perimeter_edges.append(edge)

        if perimeter_edges:
            for r in [18.0, 16.0, 14.0, 12.0, 8.0, 4.0]:
                try:
                    temp_shape = body_solid_shape.makeFillet(r, perimeter_edges)
                    if temp_shape and temp_shape.isValid() and temp_shape.Volume > 0:
                        body_solid_shape = temp_shape
                        break
                except Exception:
                    pass
                finally:
                    gc.collect()
    except Exception as e:
        App.Console.PrintError(f"Perimeter filleting failed: {str(e)}\n")

    try:
        arm_angle = 10.0  
        cut_x_start = -310.0 
        cut_y_start = -40.0 
        forearm_axis = App.Vector(1.0, 0.15 * side_multiplier, 0.0)
        arm_rot = App.Rotation(forearm_axis, -arm_angle * side_multiplier)
        y_box_offset = -250 if is_left_handed else 0
        cutter_shape = Part.makeBox(500, 250, 100)  
        placement = App.Placement(App.Vector(cut_x_start, cut_y_start + y_box_offset, 13.0), arm_rot, App.Vector(0, -y_box_offset, 0))
        cutter_shape.transformShape(placement.toMatrix())
        body_solid_shape = body_solid_shape.cut(cutter_shape)
    except Exception as e:
        App.Console.PrintError(f"Failed to apply forearm cutaway slant: {str(e)}\n")

    try:
        cone_r1 = 250.0  
        cone_r2 = 25.0   
        cone_h = 45.0   
        belly_shape = Part.makeCone(cone_r1, cone_r2, cone_h)  
        belly_x = 220.0
        belly_y = 165.0 * side_multiplier
        belly_rot = App.Rotation(App.Vector(0, 0, 1), -90)
        belly_placement = App.Placement(App.Vector(belly_x - cone_h/2, belly_y, -31.0 + cone_h/2 * side_multiplier), belly_rot)
        belly_shape.transformShape(belly_placement.toMatrix())
        body_solid_shape = body_solid_shape.cut(belly_shape)
    except Exception as e:
        App.Console.PrintError(f"Failed to apply ergonomic belly scoop: {str(e)}\n")

    try:
        cutaway_edges = []
        for edge in body_solid_shape.Edges:
            bbox = edge.BoundBox
            is_belly_edge = bbox.XMin > 100.0 and (bbox.Center.y * side_multiplier) > 100.0 and bbox.ZMax < 5.0
            is_forearm_edge = bbox.XMax < 100.0 and bbox.Center.z > 0.0 and abs(bbox.Center.y - (-40.0 * side_multiplier)) > 50.0
            if is_belly_edge or is_forearm_edge:
                cutaway_edges.append(edge)

        if cutaway_edges:
            for radius in [10.0, 8.0, 6.0, 4.0, 2.0]:
                try:
                    temp_shape = body_solid_shape.makeFillet(radius, cutaway_edges)
                    if temp_shape and temp_shape.isValid() and temp_shape.Volume > 0:
                        body_solid_shape = temp_shape
                        break
                except Exception:
                    pass
                finally:
                    gc.collect()
    except Exception as e:
        App.Console.PrintError(f"Ergonomic cutaway filleting failed: {str(e)}\n")


# ==========================================
# --- 6. SUBTRACTIVE POCKETS & HARDWARE ---
# ==========================================

if body_solid_shape and not body_solid_shape.isNull():
    # 1. Carve Main Control Cavities & Pot Pass-Throughs into Body Shell
    cavity_ops = [
        ("cavity", 39.0, -32.0, "CavityRoute"),
        ("cavity_flange", 6.0, -32.0, "CavityFlangeRoute"),
        ("pot_holes", 50.0, -32.0, "PotHolesRoute")
    ]
    
    for key, depth, z_pos, name in cavity_ops:
        if key in FILES:
            tool_shape = create_svg_solid(FILES[key], depth, name, doc)
            if tool_shape:
                bbox = tool_shape.BoundBox
                tool_shape.translate(App.Vector(-((bbox.XMin + bbox.XMax) / 2.0), -((bbox.YMin + bbox.YMax) / 2.0), -bbox.ZMin))
                tool_shape.translate(App.Vector(0.0, controls_y, z_pos))
                body_solid_shape = body_solid_shape.cut(tool_shape)

    # 2. Derive 5 Screw Centers Using Radial Intersections Across Flange Ledge
    m3_coords = []
    try:
        flange_ref = create_svg_solid(FILES["cavity_flange"], 6.0, "FlangeRef", doc)
        cavity_ref = create_svg_solid(FILES["cavity"], 35.0, "CavityRef", doc)

        if flange_ref and cavity_ref:
            b_f = flange_ref.BoundBox
            flange_ref.translate(App.Vector(-((b_f.XMin + b_f.XMax) / 2.0), -((b_f.YMin + b_f.YMax) / 2.0), -b_f.ZMin))
            flange_ref.translate(App.Vector(0.0, controls_y, -32.0))

            b_c = cavity_ref.BoundBox
            cavity_ref.translate(App.Vector(-((b_c.XMin + b_c.XMax) / 2.0), -((b_c.YMin + b_c.YMax) / 2.0), -b_c.ZMin))
            cavity_ref.translate(App.Vector(0.0, controls_y, -32.0))

            ledge_ring_solid = flange_ref.cut(cavity_ref)

            angles_deg = [30.0, 102.0, 174.0, 246.0, 318.0]
            center_pt = App.Vector(0.0, controls_y, -29.0)

            for angle in angles_deg:
                rad = math.radians(angle)
                dir_vec = App.Vector(math.cos(rad), math.sin(rad), 0.0)
                ray_line = Part.makeLine(center_pt, center_pt + (dir_vec * 200.0))
                
                intersect = ledge_ring_solid.common(ray_line)
                if intersect and not intersect.isNull() and intersect.Edges:
                    e = intersect.Edges[0]
                    p_mid = e.valueAt((e.FirstParameter + e.LastParameter) / 2.0)
                    m3_coords.append(App.Vector(p_mid.x, p_mid.y, -31.0))

    except Exception as radial_err:
        App.Console.PrintWarning(f"Radial flange sampling failed: {str(radial_err)}\n")

    if len(m3_coords) < 5:
        m3_coords = [
            App.Vector(-52.0, controls_y + 28.0, -31.0),
            App.Vector(12.0, controls_y + 34.0, -31.0),
            App.Vector(54.0, controls_y + 12.0, -31.0),
            App.Vector(38.0, controls_y - 30.0, -31.0),
            App.Vector(-42.0, controls_y - 28.0, -31.0)
        ]

    # 3. Drill M3 Pilot Holes Upward into Body Ledge
    body_m3_pilot_cutters = [
        Part.makeCylinder(1.25, 10.0, App.Vector(pt.x, pt.y, -31.0), App.Vector(0, 0, 1))
        for pt in m3_coords
    ]

    if body_m3_pilot_cutters and body_solid_shape:
        body_solid_shape = body_solid_shape.cut(Part.makeCompound(body_m3_pilot_cutters))
        App.Console.PrintMessage("Successfully cut 5 M3 pilot holes into cavity flange ledge.\n")

    # 4. Generate Control Cavity Cover (5.5mm depth)
    cover_raw = create_svg_solid(FILES["cavity_flange"], 5.5, "ControlCavityCover", doc)
    if cover_raw:
        bbox_cov = cover_raw.BoundBox
        cx_cov = (bbox_cov.XMin + bbox_cov.XMax) / 2.0
        cy_cov = (bbox_cov.YMin + bbox_cov.YMax) / 2.0
        cover_raw.translate(App.Vector(-cx_cov, -cy_cov, -bbox_cov.ZMin))
        cover_raw.translate(App.Vector(0.0, controls_y, -31.0))

        try:
            shrunk_cover = cover_raw.makeOffsetShape(-print_clearance, 0.01, fill=True)
            if shrunk_cover and shrunk_cover.isValid() and shrunk_cover.Volume > 0:
                cover_raw = shrunk_cover
        except Exception:
            pass

        cover_cutters = []
        for pt in m3_coords:
            shaft = Part.makeCylinder(1.6, 12.0, App.Vector(pt.x, pt.y, -32.0), App.Vector(0, 0, 1))
            csink = Part.makeCone(3.0, 1.6, 1.4, App.Vector(pt.x, pt.y, -31.0), App.Vector(0, 0, 1))
            cover_cutters.extend([shaft, csink])

        cover_solid = cover_raw.cut(Part.makeCompound(cover_cutters))

        cover_feature = doc.addObject("Part::Feature", "ControlCavityCover")
        cover_feature.Shape = cover_solid
        cover_feature.ViewObject.ShapeColor = (0.12, 0.12, 0.12)
        cover_feature.Label = "ControlCavityCover"
        App.Console.PrintMessage("Successfully generated ControlCavityCover with radial M3 countersinks.\n")

    # Cut body pocket using FULL-SCALE un-cut core blank tool
    try:
        pocket_cutter = full_scale_core_blank.copy()
        if pocket_cutter and not pocket_cutter.isNull():
            try:
                tolerance_cutter = pocket_cutter.makeOffsetShape(0.2, 0.01, fill=True)
                if tolerance_cutter and not tolerance_cutter.isNull() and tolerance_cutter.Volume > 0:
                    pocket_cutter = tolerance_cutter
            except Exception:
                pass

            body_solid_shape = body_solid_shape.cut(pocket_cutter)
            App.Console.PrintMessage("Successfully carved full-scale core pocket into Body Shell.\n")
    except Exception as pocket_err:
        App.Console.PrintError(f"Failed to cut core pocket: {str(pocket_err)}\n")

    # M5 Screw Pass-Through Holes & Back Surface Countersinks in Body
    try:
        m5_body_screw_cutters = []
        for mx in m5_screw_x_coords:
            for my in m5_screw_y_coords:
                pass_shaft = Part.makeCylinder(2.75, 40.0, App.Vector(mx, my * side_multiplier, -32.0), App.Vector(0, 0, 1))
                csink_cone = Part.makeCone(5.0, 2.75, 4.5, App.Vector(mx, my * side_multiplier, -31.0), App.Vector(0, 0, 1))
                m5_body_screw_cutters.extend([pass_shaft, csink_cone])

        if m5_body_screw_cutters:
            body_solid_shape = body_solid_shape.cut(Part.makeCompound(m5_body_screw_cutters))
            App.Console.PrintMessage("Successfully cut M5 screw holes and 90-degree back countersinks into Body.\n")
    except Exception as screw_err:
        App.Console.PrintWarning(f"M5 body screw processing failed: {str(screw_err)}\n")

    try:
        insert_radius = 3.4 
        butt_x = -93.0  
        try:
            test_line = Part.makeLine(App.Vector(-500.0, -45.0, -9.0), App.Vector(0.0, -45.0, -9.0))
            intersect = body_solid_shape.common(test_line)
            if intersect and not intersect.isNull() and intersect.Vertexes:
                butt_x = min(v.Point.x for v in intersect.Vertexes)
        except Exception: pass
        
        butt_insert_hole = Part.makeCylinder(insert_radius, 26.0, App.Vector(butt_x - 1.0, -45.0, -9.0), App.Vector(1, 0, 0))
        
        horn_x, horn_y = 458.0, 115.0 * side_multiplier  
        horn_pts = [v.Point for v in body_solid_shape.Vertexes if v.Point.x > 400.0]
        if horn_pts:
            horn_pts.sort(key=lambda p: p.x, reverse=True)
            horn_x, horn_y = horn_pts[0].x, horn_pts[0].y
            
        horn_insert_hole = Part.makeCylinder(insert_radius, 26.0, App.Vector(horn_x + 1.0, horn_y, -9.0), App.Vector(-1, 0, 0))
        body_solid_shape = body_solid_shape.cut(Part.makeCompound([butt_insert_hole, horn_insert_hole]))
    except Exception as strap_err:
        App.Console.PrintWarning(f"Strap button hole processing failed: {str(strap_err)}\n")

    if include_gk_channel and gk_channel_solid and not gk_channel_solid.isNull():
        try:
            body_solid_shape = body_solid_shape.cut(gk_channel_solid)
            App.Console.PrintMessage("Cut GK-3 pickup wire channel into Body Shell.\n")
        except Exception as gk_body_err:
            App.Console.PrintWarning(f"Body wire tubing cut failed: {str(gk_body_err)}\n")

    body_feature = doc.addObject("Part::Feature", "FinalBodyShell")
    body_feature.Shape = body_solid_shape
    body_feature.ViewObject.ShapeColor = (0.78, 0.45, 0.35)

# --- FINGER RAMP GENERATION ---
try:
    ramp_wire = create_ramp_wire(75.0, 0.0, 110.0, 6.0, 11.0, 500.0)
    ramp_face = Part.Face(ramp_wire)
    ramp_solid = ramp_face.extrude(App.Vector(80.0, 0, 0))
    ramp_feature = doc.addObject("Part::Feature", "FingerRamp")
    ramp_feature.Shape = ramp_solid
    ramp_feature.ViewObject.ShapeColor = (0.15, 0.15, 0.15)
    ramp_feature.Label = "FingerRamp"
    App.Console.PrintMessage("Successfully generated FingerRamp.\n")
except Exception as ramp_err:
    App.Console.PrintError(f"Failed to generate finger ramp: {str(ramp_err)}\n")


# ==========================================
# --- 7. DESIGN SYNCHRONIZED FRETBOARD -----
# ==========================================

try:
    heel_y_coords = [v.Point.y for v in full_scale_core_blank.Vertexes if abs(v.Point.x - neck_stop_x) < 2.0]
    nut_y_coords = [v.Point.y for v in full_scale_core_blank.Vertexes if abs(v.Point.x - span_end_x) < 2.0]
    
    width_heel_core = (max(heel_y_coords) - min(heel_y_coords)) if heel_y_coords else 90.0
    width_nut_core = (max(nut_y_coords) - min(nut_y_coords)) if nut_y_coords else width_headstock_nut
    
    def get_core_neck_width(x):
        return width_heel_core + (width_nut_core - width_heel_core) * ((x - neck_stop_x) / (span_end_x - neck_stop_x))

    # Construct multi-section loft to generate smooth parabolic relief across top surface
    num_sections = 12
    fb_section_wires = []
    for i in range(num_sections + 1):
        x_curr = neck_stop_x + (i / float(num_sections)) * (span_end_x - neck_stop_x)
        w_curr = get_core_neck_width(x_curr)
        wire_curr = create_fretboard_radiused_wire(x_curr, center_y, w_curr)
        fb_section_wires.append(wire_curr)

    fretboard_solid = Part.makeLoft(fb_section_wires, True)
    
    if cf_wrap_thickness > 0.0:
        App.Console.PrintMessage("Generated Fretboard with 0.3mm artificial parabolic forward-bow relief.\n")

    target_marker_frets = [3, 5, 7, 9, 12, 15, 17, 19, 21, 24]
    marker_cutters = []
    marker_chips = []
    side_marker_cutters = []
    side_marker_chips = []
    fret_slots = []
    
    sm_length = 2.0
    sm_height = 1.5
    sm_depth = 1.5
    
    for n in range(1, 25): 
        fret_x = scale_length * (2.0 ** (-n / 12.0))
        w_fret = get_core_neck_width(fret_x)
        slot_box = create_curved_slot_cutter(fret_x, center_y, w_fret)
        fret_slots.append(slot_box)
        
        if n in target_marker_frets:
            prev_fret_x = scale_length * (2.0 ** (-(n - 1) / 12.0))
            marker_x = (fret_x + prev_fret_x) / 2.0
            fret_spacing = prev_fret_x - fret_x
            marker_length = min(6.0, fret_spacing * 0.35)
            
            w_marker = get_core_neck_width(marker_x)
            marker_width = w_marker * 0.4
            
            # Local Z positioning with relief dip adjustment
            dip_m = get_fretboard_relief_dip(marker_x)
            z_pocket_start = 22.5 - dip_m

            # Shrunk dimensions for Fret Marker Chips (0.25mm offset per side = 0.5mm overall fit)
            chip_length = max(0.5, marker_length - (2.0 * print_clearance))
            chip_width = max(0.5, marker_width - (2.0 * print_clearance))

            if n in [12, 24]:
                offset_y = marker_width * 0.25
                sub_width = marker_width * 0.35
                chip_sub_width = max(0.5, sub_width - (2.0 * print_clearance))

                # Pocket Cutters (Full scale)
                box_l = Part.makeBox(marker_length, sub_width, 4.0, App.Vector(marker_x - marker_length / 2.0, center_y - offset_y - sub_width / 2.0, z_pocket_start))
                box_r = Part.makeBox(marker_length, sub_width, 4.0, App.Vector(marker_x - marker_length / 2.0, center_y + offset_y - sub_width / 2.0, z_pocket_start))
                marker_cutters.extend([box_l, box_r])

                # Marker Chips (Clearance applied)
                chip_l = Part.makeBox(chip_length, chip_sub_width, 4.0, App.Vector(marker_x - chip_length / 2.0, center_y - offset_y - chip_sub_width / 2.0, z_pocket_start))
                chip_r = Part.makeBox(chip_length, chip_sub_width, 4.0, App.Vector(marker_x - chip_length / 2.0, center_y + offset_y - chip_sub_width / 2.0, z_pocket_start))
                marker_chips.extend([chip_l, chip_r])
            else:
                box_marker = Part.makeBox(marker_length, marker_width, 4.0, App.Vector(marker_x - marker_length / 2.0, center_y - marker_width / 2.0, z_pocket_start))
                marker_cutters.append(box_marker)

                chip_marker = Part.makeBox(chip_length, chip_width, 4.0, App.Vector(marker_x - chip_length / 2.0, center_y - marker_width / 2.0, z_pocket_start))
                marker_chips.append(chip_marker)
            
            # --- Side Marker Processing (Unchanged) ---
            ry_marker = w_marker / 2.0
            z_peak_marker = (17.0 + 7.0) - dip_m
            z_edge = (z_peak_marker - 500.0) + math.sqrt(500.0**2 - ry_marker**2)
            z_mid_face = 17.0 + (z_edge - 17.0) / 2.0
            z_start_sm = z_mid_face - sm_height / 2.0
            edge_y = center_y + side_multiplier * ry_marker
            y_start = edge_y - 0.1 if side_multiplier == -1 else edge_y - sm_depth
            
            sm_chip_len = max(0.5, sm_length - (2.0 * print_clearance))
            sm_chip_h = max(0.5, sm_height - (2.0 * print_clearance))

            if n in [12, 24]:
                spacing = 2.0
                sm_box_l = Part.makeBox(sm_length, sm_depth + 0.1, sm_height, App.Vector(marker_x - spacing - sm_length / 2.0, y_start, z_start_sm))
                sm_box_r = Part.makeBox(sm_length, sm_depth + 0.1, sm_height, App.Vector(marker_x + spacing - sm_length / 2.0, y_start, z_start_sm))
                side_marker_cutters.extend([sm_box_l, sm_box_r])

                sm_chip_l = Part.makeBox(sm_chip_len, sm_depth, sm_chip_h, App.Vector(marker_x - spacing - sm_chip_len / 2.0, y_start, z_start_sm + print_clearance))
                sm_chip_r = Part.makeBox(sm_chip_len, sm_depth, sm_chip_h, App.Vector(marker_x + spacing - sm_chip_len / 2.0, y_start, z_start_sm + print_clearance))
                side_marker_chips.extend([sm_chip_l, sm_chip_r])
            else:
                sm_box = Part.makeBox(sm_length, sm_depth + 0.1, sm_height, App.Vector(marker_x - sm_length / 2.0, y_start, z_start_sm))
                side_marker_cutters.append(sm_box)

                sm_chip = Part.makeBox(sm_chip_len, sm_depth, sm_chip_h, App.Vector(marker_x - sm_chip_len / 2.0, y_start, z_start_sm + print_clearance))
                side_marker_chips.append(sm_chip)

    # --- RADIUS CROWNING FOR MAIN FRET MARKER CHIPS ---
    crowned_marker_chips = []
    if marker_chips:
        try:
            # Create a copy of the fretboard solid to use as the trimming volume
            fb_crown_tool = fretboard_solid.copy()
            
            for chip in marker_chips:
                # Intersect the taller marker block with the radiused fretboard volume
                crowned_chip = chip.common(fb_crown_tool)
                if crowned_chip and not crowned_chip.isNull() and crowned_chip.Volume > 0:
                    crowned_marker_chips.append(crowned_chip)
                else:
                    crowned_marker_chips.append(chip)
            App.Console.PrintMessage("Successfully crowned fretboard marker chips with 500mm radius.\n")
        except Exception as crown_err:
            App.Console.PrintWarning(f"Fret marker crowning bypassed: {str(crown_err)}\n")
            crowned_marker_chips = marker_chips

    # Standalone Fretboard Marker Chips (Crowned to Fretboard Radius)
    if crowned_marker_chips:
        chips_feature = doc.addObject("Part::Feature", "FretMarkers")
        chips_feature.Shape = Part.makeCompound(crowned_marker_chips)
        chips_feature.ViewObject.ShapeColor = (0.95, 0.95, 0.90)  # Off-white/pearl
        chips_feature.Label = "FretMarkers"

    if side_marker_chips:
        side_chips_feature = doc.addObject("Part::Feature", "SideFretMarkers")
        side_chips_feature.Shape = Part.makeCompound(side_marker_chips)
        side_chips_feature.ViewObject.ShapeColor = (1.0, 1.0, 1.0)
        side_chips_feature.Label = "SideFretMarkers"

    # Cut full-scale inlay pockets into Fretboard
    if marker_cutters:
        fretboard_solid = fretboard_solid.cut(Part.makeCompound(marker_cutters))
    if side_marker_cutters:
        fretboard_solid = fretboard_solid.cut(Part.makeCompound(side_marker_cutters))
    if fret_slots:
        fretboard_solid = fretboard_solid.cut(Part.makeCompound(fret_slots))
        
    fretboard_feature = doc.addObject("Part::Feature", "FinalFretboard")
    fretboard_feature.Shape = fretboard_solid
    fretboard_feature.ViewObject.ShapeColor = (0.12, 0.12, 0.12)  
    fretboard_feature.Label = "FinalFretboard"

except Exception as e:
    App.Console.PrintError(f"Failed to generate synchronized fretboard: {str(e)}\n")

# ==========================================
# --- 8. DESIGN SLEEK GRADIENT NUT ---------
# ==========================================

try:
    # --- 8.1 CONFIGURATION & PARAMETERS ---
    nut_thickness = 6.0          # Thickness along X axis (mm)
    nut_x_start = span_end_x     # Aligned flush behind nut position at X = 864mm
    fretboard_radius = 500.0     # Crown radius (mm)
    edge_clearance = 3.0         # Distance from outer string edge to nut side edge (mm)
    
    # Imperial string gauges converted to mm
    gauges_in_inches = [0.130, 0.105, 0.085, 0.065, 0.045, 0.030]  # B, E, A, D, G, C
    string_diameters = [g * 25.4 for g in gauges_in_inches]
    
    # Target height above fretboard surface at slot bottom (B = 1.60mm -> C = 1.30mm)
    string_heights = [1.60 - (i / 5.0) * (1.60 - 1.30) for i in range(6)]

    nut_width = width_headstock_nut
    nut_y_min = center_y - (nut_width / 2.0)
    nut_y_max = center_y + (nut_width / 2.0)

    z_fretboard_surface = 17.0 + 7.0  # Z = 24.0mm
    z_nut_base = z_fretboard_surface - 2.5  # Seated 2.5mm into core slot (Z = 21.5mm)

    # --- 8.2 HANDEDNESS & GRADIENT HEIGHT CALCULATIONS ---
    if is_left_handed:
        # Left-handed: B string on Y_min (bottom), C string on Y_max (top)
        y_b_center = nut_y_min + edge_clearance + (string_diameters[0] / 2.0)
        y_c_center = nut_y_max - edge_clearance - (string_diameters[5] / 2.0)
        y_b_edge = nut_y_min
        y_c_edge = nut_y_max
    else:
        # Right-handed: B string on Y_max (top), C string on Y_min (bottom)
        y_b_center = nut_y_max - edge_clearance - (string_diameters[0] / 2.0)
        y_c_center = nut_y_min + edge_clearance + (string_diameters[5] / 2.0)
        y_b_edge = nut_y_max
        y_c_edge = nut_y_min

    string_centers_y = [
        y_b_center + (i / 5.0) * (y_c_center - y_b_center) for i in range(6)
    ]

    # Nut top crest height above fretboard = Slot Bottom Height + 1.0x String Diameter
    h_b_top = 2.5 + string_heights[0] + string_diameters[0]  
    h_c_top = 2.5 + string_heights[5] + string_diameters[5]  

    # --- 8.3 BUILD GRADIENT TAPERED NUT BLANK ---
    def get_crowned_z(y, y_edge_b, h_b, y_edge_c, h_c):
        ry = y - center_y
        z_crown_rel = math.sqrt(fretboard_radius**2 - ry**2) - math.sqrt(fretboard_radius**2 - (nut_width/2.0)**2)
        t = (y - y_edge_b) / (y_edge_c - y_edge_b)
        h_grad = h_b + t * (h_c - h_b)
        return z_nut_base + h_grad + z_crown_rel

    num_pts = 16
    wire_pts = []
    for i in range(num_pts + 1):
        curr_y = y_b_edge + (i / float(num_pts)) * (y_c_edge - y_b_edge)
        curr_z = get_crowned_z(curr_y, y_b_edge, h_b_top, y_c_edge, h_c_top)
        wire_pts.append(App.Vector(nut_x_start, curr_y, curr_z))

    top_curve = Part.BSplineCurve()
    top_curve.interpolate(wire_pts)
    e_top = top_curve.toShape()

    p_bot_b = App.Vector(nut_x_start, y_b_edge, z_nut_base)
    p_bot_c = App.Vector(nut_x_start, y_c_edge, z_nut_base)

    e_side_b = Part.makeLine(wire_pts[0], p_bot_b)
    e_bottom = Part.makeLine(p_bot_b, p_bot_c)
    e_side_c = Part.makeLine(p_bot_c, wire_pts[-1])

    nut_wire = Part.Wire([e_top, e_side_c, e_bottom, e_side_b])
    nut_sculpted = Part.Face(nut_wire).extrude(App.Vector(nut_thickness, 0, 0))

    # --- 8.4 FILLET ONLY REAR VERTICAL CORNERS (TUNER SIDE) ---
    rear_vertical_edges = []
    for edge in nut_sculpted.Edges:
        bbox = edge.BoundBox
        is_vert_side = abs(bbox.XMin - bbox.XMax) < 0.1 and abs(bbox.ZMax - bbox.ZMin) > 2.0
        is_outer_y = abs(bbox.Center.y - nut_y_min) < 1.0 or abs(bbox.Center.y - nut_y_max) < 1.0
        # Exclude front edges facing fretboard (X = nut_x_start) to keep seamless joint
        is_rear_x = abs(bbox.Center.x - (nut_x_start + nut_thickness)) < 0.2
        
        if is_vert_side and is_outer_y and is_rear_x:
            rear_vertical_edges.append(edge)

    if rear_vertical_edges:
        for r_side in [2.0, 1.5, 1.0]:
            try:
                temp_nut = nut_sculpted.makeFillet(r_side, rear_vertical_edges)
                if temp_nut and temp_nut.isValid() and temp_nut.Volume > 0:
                    nut_sculpted = temp_nut
                    break
            except Exception:
                pass

    # --- 8.5 CARVE OPEN U-SHAPED SLOTS ---
    slot_cutters = []
    for i in range(6):
        sy = string_centers_y[i]
        s_dia = string_diameters[i]
        s_h = string_heights[i]

        ry = sy - center_y
        z_crown = (z_fretboard_surface - fretboard_radius) + math.sqrt(fretboard_radius**2 - ry**2)
        z_slot_bottom = z_crown + s_h

        # Cylinder forms the rounded 180-degree bottom saddle
        cyl_slot = Part.makeCylinder(
            s_dia / 2.0, nut_thickness + 2.0,
            App.Vector(nut_x_start - 1.0, sy, z_slot_bottom + (s_dia / 2.0)),
            App.Vector(1, 0, 0)
        )
        
        # Box cutter extends 15mm UPWARDS to guarantee a clean open top slot
        box_slot = Part.makeBox(
            nut_thickness + 2.0, s_dia, 15.0,
            App.Vector(nut_x_start - 1.0, sy - (s_dia / 2.0), z_slot_bottom + (s_dia / 2.0))
        )
        slot_cutters.extend([cyl_slot, box_slot])

    nut_sculpted = nut_sculpted.cut(Part.makeCompound(slot_cutters))

    # --- 8.6 FILLET TUNER-SIDE ROLLED SADDLE EDGES ---
    tuner_side_edges = []
    for edge in nut_sculpted.Edges:
        bbox = edge.BoundBox
        is_tuner_x = abs(bbox.Center.x - (nut_x_start + nut_thickness)) < 0.2
        is_top_z = bbox.ZMin > z_fretboard_surface
        if is_tuner_x and is_top_z:
            tuner_side_edges.append(edge)

    if tuner_side_edges:
        for r_tuner in [1.0, 0.8, 0.5]:
            try:
                temp_nut = nut_sculpted.makeFillet(r_tuner, tuner_side_edges)
                if temp_nut and temp_nut.isValid() and temp_nut.Volume > 0:
                    nut_sculpted = temp_nut
                    break
            except Exception:
                pass

    # --- 8.7 ADD NUT FEATURE TO FREECAD DOCUMENT ---
    nut_feature = doc.addObject("Part::Feature", "CustomNut")
    nut_feature.Shape = nut_sculpted
    nut_feature.ViewObject.ShapeColor = (0.22, 0.22, 0.24)  # Graphite / Tusq look
    nut_feature.Label = "CustomNut"
    App.Console.PrintMessage("Successfully generated custom gradient 6-string nut with flush fretboard interface.\n")

except Exception as nut_err:
    App.Console.PrintError(f"Failed to generate custom nut: {str(nut_err)}\n")

# ==========================================
# --- 9. ROUTING TEMPLATES GENERATION -----
# ==========================================

template_thickness = 12.0  # Standard MDF / Acrylic template thickness (mm)
z_template_base = -60.0    # Offset plane to avoid visual overlap

# --- HELPER: Extrude True SVG Silhouette Wire ---
def build_contour_template(svg_filepath, cutters_list, name, color_rgb, translation_vector=App.Vector(0,0,0)):
    try:
        # Import SVG to get exact planar perimeter
        old_objs = set(doc.Objects)
        importSVG.insert(svg_filepath, doc.Name)
        doc.recompute()
        
        new_objs = [o for o in doc.Objects if o not in old_objs and hasattr(o, 'Shape') and not o.Shape.isNull()]
        
        if not new_objs:
            return None
            
        # Find largest outer contour shape
        outer_obj = max(new_objs, key=lambda o: (o.Shape.BoundBox.XMax - o.Shape.BoundBox.XMin) * (o.Shape.BoundBox.YMax - o.Shape.BoundBox.YMin))
        wire_shape = outer_obj.Shape.OuterWire if hasattr(outer_obj.Shape, "OuterWire") else outer_obj.Shape.Wires[0]
        
        template_face = Part.Face(wire_shape)
        template_solid = template_face.extrude(App.Vector(0, 0, template_thickness))
        
        # Apply body translation alignment
        if translation_vector.Length > 0:
            template_solid.translate(translation_vector)
            
        # Shift to template Z height
        template_solid.translate(App.Vector(0, 0, z_template_base - template_solid.BoundBox.ZMin))

        # Cleanup temporary SVG import objects
        for o in new_objs:
            try: doc.removeObject(o.Name)
            except Exception: pass

        # Cut holes, pockets, and channels
        if cutters_list:
            comp_cutters = Part.makeCompound(cutters_list)
            template_solid = template_solid.cut(comp_cutters)

        feat = doc.addObject("Part::Feature", name)
        feat.Shape = template_solid
        feat.ViewObject.ShapeColor = color_rgb
        feat.ViewObject.Transparency = 20
        feat.Label = name
        return feat
    except Exception as template_err:
        App.Console.PrintError(f"Failed to generate template {name}: {str(template_err)}\n")
        return None


# --- 9.1 STRUCTURAL CORE TEMPLATE (FLAT SOLID EXTRUSION METHOD) ---
core_template_cutters = []

# 1. Pilot Holes: 12-Node Array (3.0mm pilot)
for x in [-15.0, 15.0]:
    for y in [-45.0, -27.0, -9.0, 9.0, 27.0, 45.0]:
        core_template_cutters.append(
            Part.makeCylinder(1.5, 50.0, App.Vector(x, y, z_template_base - 5.0), App.Vector(0, 0, 1))
        )

# 2. Pilot Holes: M5 Core Mounts (2.5mm pilot)
for mx in m5_screw_x_coords:
    for my in m5_screw_y_coords:
        core_template_cutters.append(
            Part.makeCylinder(2.5, 50.0, App.Vector(mx, my * side_multiplier, z_template_base - 5.0), App.Vector(0, 0, 1))
        )

# 3. Pilot Holes: Tuner Pegs (3.0mm center pilot)
for t_cyl in tuner_cutters:
    t_center = t_cyl.BoundBox.Center
    core_template_cutters.append(
        Part.makeCylinder(1.5, 50.0, App.Vector(t_center.x, t_center.y, z_template_base - 5.0), App.Vector(0, 0, 1))
    )

# 4. Routing Voids: 3 DISCRETE INDIVIDUAL SLOTS (Truss Rod & CF Rods)
if cf_wrap_thickness == 0.0:
    cf_rod_w = 3.5
    cf_offset_y = 15.0

    # Left Carbon Fiber Rod Slot
    cf_slot_left = Part.makeBox(
        625.0, cf_rod_w, 50.0,
        App.Vector(215.0, center_y - cf_offset_y - (cf_rod_w / 2.0), z_template_base - 5.0)
    )
    
    # Right Carbon Fiber Rod Slot
    cf_slot_right = Part.makeBox(
        625.0, cf_rod_w, 50.0,
        App.Vector(215.0, center_y + cf_offset_y - (cf_rod_w / 2.0), z_template_base - 5.0)
    )

    # Center Truss Rod Slot
    truss_slot = Part.makeBox(
        610.0, 6.35, 50.0,
        App.Vector(neck_stop_x, center_y - 6.35 / 2.0, z_template_base - 5.0)
    )

    # Truss Rod Access Pocket
    truss_access_void = Part.makeBox(
        35.5, 10.0, 50.0,
        App.Vector(neck_stop_x - 30.0, center_y - 10.0 / 2.0, z_template_base - 5.0)
    )

    core_template_cutters.extend([cf_slot_left, cf_slot_right, truss_slot, truss_access_void])

try:
    y_heel = width_heel / 2.0
    y_bridge = bridge_core_width / 2.0
    y_nut = width_headstock_nut / 2.0

    # A. Rectangular Bridge Block (Flat Extrusion)
    poly_brg = Part.makePolygon([
        App.Vector(bridge_start_x, -y_bridge, z_template_base),
        App.Vector(taper_start_x, -y_bridge, z_template_base),
        App.Vector(taper_start_x, y_bridge, z_template_base),
        App.Vector(bridge_start_x, y_bridge, z_template_base),
        App.Vector(bridge_start_x, -y_bridge, z_template_base)
    ])
    t_bridge_block = Part.Face(poly_brg).extrude(App.Vector(0, 0, template_thickness))

    # B. Tapered Bridge-to-Heel Transition
    poly_taper = Part.makePolygon([
        App.Vector(taper_start_x, -y_bridge, z_template_base),
        App.Vector(neck_stop_x, -y_heel, z_template_base),
        App.Vector(neck_stop_x, y_heel, z_template_base),
        App.Vector(taper_start_x, y_bridge, z_template_base),
        App.Vector(taper_start_x, -y_bridge, z_template_base)
    ])
    t_taper_block = Part.Face(poly_taper).extrude(App.Vector(0, 0, template_thickness))

    # C. Playing Length Neck Taper (Heel to Nut)
    poly_neck = Part.makePolygon([
        App.Vector(neck_stop_x, -y_heel, z_template_base),
        App.Vector(span_end_x, -y_nut, z_template_base),
        App.Vector(span_end_x, y_nut, z_template_base),
        App.Vector(neck_stop_x, y_heel, z_template_base),
        App.Vector(neck_stop_x, -y_heel, z_template_base)
    ])
    t_neck_block = Part.Face(poly_neck).extrude(App.Vector(0, 0, template_thickness))

    # D. Headstock SVG Solid Flat Extrusion
    t_headstock_block = headstock_svg_face.extrude(App.Vector(0, 0, template_thickness))
    t_headstock_block.translate(App.Vector(0, 0, z_template_base - t_headstock_block.BoundBox.ZMin))

    # E. Fuse primitive solids into unified flat template shape
    core_solid_template = t_bridge_block.fuse(t_taper_block).fuse(t_neck_block).fuse(t_headstock_block)

    # F. Cut holes, rod channels, and tuner pilots
    if core_template_cutters:
        core_solid_template = core_solid_template.cut(Part.makeCompound(core_template_cutters))

    feat_c = doc.addObject("Part::Feature", "Template_StructuralCore")
    feat_c.Shape = core_solid_template
    feat_c.ViewObject.ShapeColor = (0.85, 0.85, 0.20)
    feat_c.ViewObject.Transparency = 20
    feat_c.Label = "Template_StructuralCore"
    App.Console.PrintMessage("Successfully generated exact flat-extruded Structural Core template.\n")

except Exception as core_t_err:
    App.Console.PrintError(f"Failed Structural Core template generation: {str(core_t_err)}\n")

# --- 9.2 FINAL BODY SHELL - FRONT TEMPLATE ---
body_front_cutters = []

# 1. Routing Void: Core Pocket Area matching Template_StructuralCore outline
if 'core_solid_template' in locals() and core_solid_template:
    try:
        core_pocket_void = core_solid_template.extrude(App.Vector(0, 0, 50.0))
        core_pocket_void.translate(App.Vector(0, 0, z_template_base - 10.0))
        body_front_cutters.append(core_pocket_void)
    except Exception:
        poly_pocket = Part.makePolygon([
            App.Vector(bridge_start_x, -y_bridge, z_template_base - 5.0),
            App.Vector(taper_start_x, -y_bridge, z_template_base - 5.0),
            App.Vector(neck_stop_x, -y_heel, z_template_base - 5.0),
            App.Vector(neck_stop_x, y_heel, z_template_base - 5.0),
            App.Vector(taper_start_x, y_bridge, z_template_base - 5.0),
            App.Vector(bridge_start_x, y_bridge, z_template_base - 5.0),
            App.Vector(bridge_start_x, -y_bridge, z_template_base - 5.0)
        ])
        body_front_cutters.append(Part.Face(poly_pocket).extrude(App.Vector(0, 0, 50.0)))

# 2. Pilot Holes & Pass-Throughs for Pot / Control Holes
if "pot_holes" in FILES:
    old_objs = set(doc.Objects)
    try:
        importSVG.insert(FILES["pot_holes"], doc.Name)
        doc.recompute()
        pot_svg_objs = [o for o in doc.Objects if o not in old_objs and hasattr(o, 'Shape') and not o.Shape.isNull()]

        if pot_svg_objs:
            # Calculate overall bounding box for the entire SVG group to preserve relative coordinates
            group_xmin = min(o.Shape.BoundBox.XMin for o in pot_svg_objs)
            group_xmax = max(o.Shape.BoundBox.XMax for o in pot_svg_objs)
            group_ymin = min(o.Shape.BoundBox.YMin for o in pot_svg_objs)
            group_ymax = max(o.Shape.BoundBox.YMax for o in pot_svg_objs)

            group_cx = (group_xmin + group_xmax) / 2.0
            group_cy = (group_ymin + group_ymax) / 2.0

            for p_obj in pot_svg_objs:
                r, center = get_circle_properties(p_obj.Shape)
                
                # Transform local SVG center to aligned control placement
                cx = (center.x - group_cx)
                cy = (center.y - group_cy) + controls_y

                # Set radius: 1.5mm pilot for holes > 3mm dia (R > 1.5mm), else keep original radius
                cutter_r = 1.5 if r > 1.5 else r
                
                pot_pilot = Part.makeCylinder(cutter_r, 50.0, App.Vector(cx, cy, z_template_base - 5.0), App.Vector(0, 0, 1))
                body_front_cutters.append(pot_pilot)

        for p_obj in pot_svg_objs:
            try: doc.removeObject(p_obj.Name)
            except Exception: pass

    except Exception as pot_err:
        App.Console.PrintWarning(f"Pot hole pilot extraction failed: {str(pot_err)}\n")

build_contour_template(FILES["body_contour"], body_front_cutters, "Template_BodyShell_Front", (0.20, 0.70, 0.85), body_translation)

# --- 9.3 FINAL BODY SHELL - BACK TEMPLATE (CONTROL CAVITY SIDE) ---
body_back_cutters = []

# Control Cavity & Flange Ledge Route Voids
for key in ["cavity", "cavity_flange"]:
    if key in FILES:
        cav_void = create_svg_solid(FILES[key], 50.0, f"{key}_TemplateVoid", doc)
        if cav_void:
            b_c = cav_void.BoundBox
            cav_void.translate(App.Vector(-((b_c.XMin + b_c.XMax) / 2.0), -((b_c.YMin + b_c.YMax) / 2.0), z_template_base - 5.0))
            cav_void.translate(App.Vector(0.0, controls_y, 0.0))
            body_back_cutters.append(cav_void)

# Pilot Holes: M3 Ledge Screws (1.5mm pilot)
for pt in m3_coords:
    body_back_cutters.append(
        Part.makeCylinder(1.5, 50.0, App.Vector(pt.x, pt.y, z_template_base - 5.0), App.Vector(0, 0, 1))
    )

# Pilot Holes: M5 Core Pass-Through Screws (2.75mm pilot)
for mx in m5_screw_x_coords:
    for my in m5_screw_y_coords:
        body_back_cutters.append(
            Part.makeCylinder(2.75, 50.0, App.Vector(mx, my * side_multiplier, z_template_base - 5.0), App.Vector(0, 0, 1))
        )

# Pilot Holes: Strap Buttons (1.5mm pilot)
body_back_cutters.append(Part.makeCylinder(1.5, 50.0, App.Vector(butt_x, -45.0, z_template_base - 5.0), App.Vector(0, 0, 1)))
body_back_cutters.append(Part.makeCylinder(1.5, 50.0, App.Vector(horn_x, horn_y, z_template_base - 5.0), App.Vector(0, 0, 1)))

build_contour_template(FILES["body_contour"], body_back_cutters, "Template_BodyShell_Back", (0.85, 0.40, 0.85), body_translation)

# ==========================================
# --- 9.4 STRUCTURAL CORE SIDE TEMPLATE ----
# ==========================================

try:
    z_side_template_base = -60.0  # Z elevation offset matching other flat templates
    y_side_template_offset = -120.0 * side_multiplier  # Shift Y position away from central axis
    
    if 'structural_core' in locals() and structural_core and not structural_core.isNull():
        # 1. Bounding dimensions of the structural core
        core_bbox = structural_core.BoundBox
        x_min_core = core_bbox.XMin
        x_max_core = core_bbox.XMax
        z_min_core = core_bbox.ZMin

        # 2. Construct 2D Side Profile Wire in local XY space (X -> X, Y -> Z elevation)
        # This guarantees Part.Face() succeeds without Null shape errors
        side_profile_2d_points = [
            App.Vector(x_min_core, z_min_core, 0.0),                     # Bottom rear bridge block corner
            App.Vector(bridge_start_x, z_bridge_bottom, 0.0),           # Bridge anchor bottom face
            App.Vector(neck_stop_x, z_bridge_bottom, 0.0),              # Heel bottom step
            App.Vector(neck_stop_x, z_neck_top - thickness_heel, 0.0),  # Heel transition curve start
            App.Vector(span_end_x, z_neck_top - 17.0, 0.0),             # Nut bottom line
            App.Vector(x_volute_end, z_neck_top - 17.0, 0.0),           # Volute transition
            App.Vector(x_max_core, z_neck_top - 17.0, 0.0),             # Headstock tip bottom
            App.Vector(x_max_core, z_neck_top, 0.0),                    # Headstock tip top
            App.Vector(span_end_x, z_neck_top, 0.0),                    # Nut top surface
            App.Vector(neck_stop_x, z_neck_top, 0.0),                   # Heel top step (Z = 17mm)
            App.Vector(neck_stop_x, z_step_interface, 0.0),             # Core step drop (Z = 13mm)
            App.Vector(bridge_start_x, z_step_interface, 0.0),          # Bridge block top face
            App.Vector(x_min_core, z_step_interface, 0.0),              # Rear tail top face
            App.Vector(x_min_core, z_min_core, 0.0)                     # Close loop
        ]

        # 3. Create Face and Extrude 12mm template thickness
        side_wire_2d = Part.makePolygon(side_profile_2d_points)
        side_face_2d = Part.Face(side_wire_2d)
        side_template_solid = side_face_2d.extrude(App.Vector(0, 0, template_thickness))

        # 4. Transform solid into XZ space: rotate -90 degrees around X-axis
        rot_xz = App.Rotation(App.Vector(1, 0, 0), -90.0)
        side_template_solid.transformShape(App.Placement(App.Vector(0, 0, 0), rot_xz).toMatrix())

        # 5. Position template to side offset location
        side_template_solid.translate(App.Vector(0, y_side_template_offset, 0))

        # 6. Drill Reference Pilot Holes (3.0mm dia) for indexing
        side_pilots = [
            # Bridge Center alignment pilot
            Part.makeCylinder(1.5, 50.0, App.Vector(0.0, y_side_template_offset - 5.0, (z_step_interface + z_bridge_bottom) / 2.0), App.Vector(0, 1, 0)),
            # Heel Interface alignment pilot (X = 211mm)
            Part.makeCylinder(1.5, 50.0, App.Vector(neck_stop_x, y_side_template_offset - 5.0, (z_neck_top + z_bridge_bottom) / 2.0), App.Vector(0, 1, 0)),
            # Scale Nut Line alignment pilot (X = 864mm)
            Part.makeCylinder(1.5, 50.0, App.Vector(span_end_x, y_side_template_offset - 5.0, z_neck_top - 8.5), App.Vector(0, 1, 0))
        ]

        side_template_solid = side_template_solid.cut(Part.makeCompound(side_pilots))

        # 7. Instantiate Feature Object
        feat_side = doc.addObject("Part::Feature", "Template_StructuralCore_Side")
        feat_side.Shape = side_template_solid
        feat_side.ViewObject.ShapeColor = (0.30, 0.85, 0.60)
        feat_side.ViewObject.Transparency = 20
        feat_side.Label = "Template_StructuralCore_Side"
        
        App.Console.PrintMessage("Successfully generated Structural Core Side Profile Template.\n")

except Exception as side_t_err:
    App.Console.PrintError(f"Failed Structural Core Side template generation: {str(side_t_err)}\n")

# ==========================================
# --- 10. ERGONOMIC ANGLED WEDGE SLEDS ----
# ==========================================

# --- 10.1 FOREARM SLANT ANGLED WEDGE SLED ---
try:
    # 1. Base block resting flat on top body surface (Z = 13.0mm)
    sled_w, sled_l, sled_h = 350.0, 250.0, 50.0
    x_start_fa = -350.0
    y_start_fa = -150.0 if is_left_handed else -50.0
    
    base_block_fa = Part.makeBox(sled_w, sled_l, sled_h, App.Vector(x_start_fa, y_start_fa, 13.0))

    # 2. Angled cutter plane (10 deg drop) to slope the top surface of the sled
    cutter_plane_fa = Part.makeBox(sled_w + 100.0, sled_l + 100.0, sled_h + 20.0)
    y_box_offset = -250 if is_left_handed else 0
    
    placement_fa = App.Placement(
        App.Vector(-310.0, -40.0 + y_box_offset, 13.0),
        App.Rotation(App.Vector(1.0, 0.15 * side_multiplier, 0.0), -10.0 * side_multiplier),
        App.Vector(0, -y_box_offset, 0)
    )
    cutter_plane_fa.transformShape(placement_fa.toMatrix())

    # 3. Trim top off base block to form a 10-degree wedge
    forearm_wedge = base_block_fa.cut(cutter_plane_fa)

    # 4. Punch central routing window through the wedge
    window_void_fa = Part.makeBox(
        220.0, 120.0, 100.0,
        App.Vector(-300.0, -100.0 if is_left_handed else -20.0, -10.0)
    )
    forearm_sled_solid = forearm_wedge.cut(window_void_fa)

    feat_fa = doc.addObject("Part::Feature", "Template_ForearmSled")
    feat_fa.Shape = forearm_sled_solid
    feat_fa.ViewObject.ShapeColor = (0.20, 0.85, 0.40)
    feat_fa.ViewObject.Transparency = 30
    feat_fa.Label = "Template_ForearmSled"
    App.Console.PrintMessage("Successfully generated Forearm Slant Angled Wedge Sled.\n")

except Exception as fa_err:
    App.Console.PrintError(f"Failed Forearm wedge sled generation: {str(fa_err)}\n")


# --- 10.2 BELLY SCOOP ANGLED WEDGE SLED ---
try:
    # 1. Base block resting flat against back body surface (Z = -31.0mm)
    sled_w_b, sled_l_b, sled_h_b = 350.0, 250.0, 50.0
    x_start_bs = 80.0
    y_start_bs = -150.0 if is_left_handed else -50.0

    base_block_bs = Part.makeBox(sled_w_b, sled_l_b, sled_h_b, App.Vector(x_start_bs, y_start_bs, -31.0 - sled_h_b))

    # 2. Angled cutter plane (12 deg drop) to slope the reference surface of the sled
    cutter_plane_bs = Part.makeBox(sled_w_b + 100.0, sled_l_b + 100.0, sled_h_b + 20.0)
    y_belly_offset = -200 if is_left_handed else 0
    
    placement_bs = App.Placement(
        App.Vector(120.0, 50.0 * side_multiplier + y_belly_offset, -31.0),
        App.Rotation(App.Vector(1.0, -0.10 * side_multiplier, 0.0), 12.0 * side_multiplier),
        App.Vector(0, -y_belly_offset, 0)
    )
    cutter_plane_bs.transformShape(placement_bs.toMatrix())

    # 3. Trim base block to form 12-degree wedge
    belly_wedge = base_block_bs.cut(cutter_plane_bs)

    # 4. Punch central routing window through the wedge
    window_void_bs = Part.makeBox(
        220.0, 120.0, 100.0,
        App.Vector(110.0, -80.0 if is_left_handed else 0.0, -80.0)
    )
    belly_sled_solid = belly_wedge.cut(window_void_bs)

    feat_bs = doc.addObject("Part::Feature", "Template_BellyScoopSled")
    feat_bs.Shape = belly_sled_solid
    feat_bs.ViewObject.ShapeColor = (0.85, 0.40, 0.20)
    feat_bs.ViewObject.Transparency = 30
    feat_bs.Label = "Template_BellyScoopSled"
    App.Console.PrintMessage("Successfully generated Belly Scoop Angled Wedge Sled.\n")

except Exception as bs_err:
    App.Console.PrintError(f"Failed Belly Scoop wedge sled generation: {str(bs_err)}\n")

# ==========================================
# --- 8.8 HEADSTOCK TOP VENEER (1MM) ------
# ==========================================

try:
    if "headstock" in FILES:
        z_veneer_top = z_neck_top + 2.0  # Floating 2mm above headstock face to avoid interactions

        # 1. Extrude 1.0mm thick main headstock plate from SVG
        veneer_headstock = create_svg_solid(FILES["headstock"], 1.0, "HeadstockVeneerSolid", doc)
        
        if veneer_headstock:
            # Shift main headstock plate to target headstock coordinates
            veneer_headstock.translate(App.Vector(target_x, target_y, z_veneer_top - 1.0))

            # 2. Loft transition veneer sheet between nut (X = 864mm) and volute boundary (X = 884mm)
            wire_nut_v = create_semi_ellipse_wire(
                span_end_x, center_y, width_headstock_nut, 1.0, z_top=z_veneer_top
            )
            wire_volute_v = create_asymmetric_rectangle_wire(
                x_volute_end, y_min_hs, y_max_hs, 1.0, z_top=z_veneer_top
            )
            veneer_transition = Part.makeLoft([wire_nut_v, wire_volute_v], True)

            # 3. Fuse aligned headstock plate and transition loft
            veneer_solid = veneer_headstock.fuse(veneer_transition)

            # 4. Trim overhang ONLY behind the nut interface (X < span_end_x)
            trim_back_veneer = Part.makeBox(
                200.0, 300.0, 100.0,
                App.Vector(span_end_x - 200.0, -150.0, z_veneer_top - 50.0)
            )
            veneer_solid = veneer_solid.cut(trim_back_veneer)

            # 5. Cut out CustomNut registration notch at X = 864mm (span_end_x)
            try:
                nut_notch_cutter = Part.makeBox(
                    nut_thickness + 0.1,  # 6.1mm width for clearance
                    width_headstock_nut + 2.0, 
                    10.0,
                    App.Vector(span_end_x, center_y - (width_headstock_nut / 2.0) - 1.0, z_veneer_top - 5.0)
                )
                
                if 'nut_sculpted' in locals() and nut_sculpted:
                    try:
                        nut_exact_cutter = nut_sculpted.copy()
                        nut_exact_cutter.translate(App.Vector(0, 0, 2.0))
                        nut_exact_cutter = nut_exact_cutter.makeOffsetShape(0.1, 0.01, fill=True)
                        if nut_exact_cutter and nut_exact_cutter.isValid():
                            nut_notch_cutter = nut_exact_cutter
                    except Exception:
                        pass

                veneer_solid = veneer_solid.cut(nut_notch_cutter)
                App.Console.PrintMessage("Successfully cut CustomNut positioning notch out of HeadstockVeneer.\n")
            except Exception as nut_notch_err:
                App.Console.PrintWarning(f"Nut notch cut bypassed: {str(nut_notch_err)}\n")

            # 6. Drill enlarged 25mm diameter tuner clearance holes through veneer
            if tuner_cutters:
                veneer_tuner_radius = 25.0 / 2.0  # 12.5mm radius
                tuner_comp = Part.makeCompound([
                    Part.makeCylinder(
                        veneer_tuner_radius, 
                        20.0, 
                        App.Vector(t.BoundBox.Center.x, t.BoundBox.Center.y, z_veneer_top - 5.0), 
                        App.Vector(0, 0, 1)
                    ) for t in tuner_cutters
                ])
                veneer_solid = veneer_solid.cut(tuner_comp)

            # 7. Cut 1.0mm logo pocket through floating veneer
            if cf_wrap_thickness == 0.0 and "logo" in FILES and 'x_shift' in locals():
                try:
                    veneer_logo_cutter = create_svg_solid(FILES["logo"], 3.0, "VeneerLogoCutter", doc)
                    if veneer_logo_cutter:
                        veneer_logo_cutter.translate(App.Vector(x_shift, y_shift, z_veneer_top - 2.0))
                        veneer_solid = veneer_solid.cut(veneer_logo_cutter)
                        App.Console.PrintMessage("Successfully cut logo pocket through HeadstockVeneer.\n")
                except Exception as v_logo_err:
                    App.Console.PrintWarning(f"Veneer logo pocket cut bypassed: {str(v_logo_err)}\n")

            # 8. Assign shape as standalone feature
            standalone_veneer_shape = veneer_solid.copy()

            veneer_feature = doc.addObject("Part::Feature", "HeadstockVeneer")
            veneer_feature.Shape = standalone_veneer_shape
            veneer_feature.ViewObject.ShapeColor = (0.20, 0.12, 0.08)  # Dark ebony aesthetic
            veneer_feature.Label = "HeadstockVeneer"
            App.Console.PrintMessage("Successfully generated complete 1.0mm HeadstockVeneer object with 25mm Tuner Washer Recesses.\n")

except Exception as veneer_err:
    App.Console.PrintError(f"Failed to generate headstock veneer: {str(veneer_err)}\n")

# ==========================================
# --- 8.9 CORE BODY TOP VENEER (1MM) ------
# ==========================================

try:
    # Landmarks for core body top veneer (X = 30mm to X = 211mm)
    v_body_x_start = 30.0
    v_body_x_end = neck_stop_x  # X = 211.0mm
    z_step_top = z_step_interface  # Z = 13.0mm (Top surface of step)
    outer_corner_radius = 2.0      # Vertical corner radius (mm)
    top_edge_radius = 0.6          # Roundover radius for outer top perimeter edges (mm)
    seam_fillet_radius = 0.8       # Fillet radius where finger ramp joins veneer plate (mm)

    # 1. Determine target bottom Z plane based on FingerRamp's ZMin
    if 'ramp_solid' in locals() and ramp_solid and not ramp_solid.isNull():
        z_veneer_bottom = ramp_solid.BoundBox.ZMin
        veneer_thickness = z_step_top - z_veneer_bottom
    else:
        z_veneer_bottom = z_step_top - 1.0
        veneer_thickness = 1.0

    # 2. Reconstruct 2D tapered profile matching core bridge block & neck heel
    y_heel = width_heel / 2.0
    y_bridge = bridge_core_width / 2.0

    def get_core_taper_width(x):
        if x <= taper_start_x:
            return y_bridge
        elif x >= neck_stop_x:
            return y_heel
        else:
            t = (x - taper_start_x) / (neck_stop_x - taper_start_x)
            return y_bridge + t * (y_heel - y_bridge)

    y_start_width = get_core_taper_width(v_body_x_start)

    # Build 2D boundary wire at matched bottom Z elevation
    poly_body_veneer = Part.makePolygon([
        App.Vector(v_body_x_start, -y_start_width, z_veneer_bottom),
        App.Vector(taper_start_x, -y_bridge, z_veneer_bottom),
        App.Vector(v_body_x_end, -y_heel, z_veneer_bottom),
        App.Vector(v_body_x_end, y_heel, z_veneer_bottom),
        App.Vector(taper_start_x, y_bridge, z_veneer_bottom),
        App.Vector(v_body_x_start, y_start_width, z_veneer_bottom),
        App.Vector(v_body_x_start, -y_start_width, z_veneer_bottom)
    ])

    # Extrude base plate sheet
    body_veneer_face = Part.Face(poly_body_veneer)
    body_veneer_solid = body_veneer_face.extrude(App.Vector(0, 0, veneer_thickness))

    # 3. FILLET OUTER PLATE VERTICAL CORNERS
    plate_vertical_edges = []
    for edge in body_veneer_solid.Edges:
        v1, v2 = edge.Vertexes[0].Point, edge.Vertexes[1].Point
        is_vertical = (abs(v1.x - v2.x) < 1e-3) and (abs(v1.y - v2.y) < 1e-3) and (abs(v1.z - v2.z) > 1e-3)
        is_at_neck_stop = max(v1.x, v2.x) >= (neck_stop_x - 0.5)

        if is_vertical and not is_at_neck_stop:
            plate_vertical_edges.append(edge)

    if plate_vertical_edges:
        try:
            body_veneer_solid = body_veneer_solid.makeFillet(outer_corner_radius, plate_vertical_edges)
            App.Console.PrintMessage("Filleted outer plate vertical edges successfully.\n")
        except Exception as plate_f_err:
            App.Console.PrintWarning(f"Plate corner filleting bypassed: {str(plate_f_err)}\n")

    # 3.5 FILLET VENEER OUTER TOP EDGES (BEFORE RAMP FUSION)
    ramp_x_start = ramp_solid.BoundBox.XMin if ('ramp_solid' in locals() and ramp_solid) else 0.0
    ramp_x_end = ramp_solid.BoundBox.XMax if ('ramp_solid' in locals() and ramp_solid) else 0.0

    top_outer_edges = []
    for edge in body_veneer_solid.Edges:
        v1, v2 = edge.Vertexes[0].Point, edge.Vertexes[1].Point
        
        is_at_top = abs(v1.z - z_step_top) < 1e-3 and abs(v2.z - z_step_top) < 1e-3
        is_at_neck_stop = (v1.x >= neck_stop_x - 0.5) or (v2.x >= neck_stop_x - 0.5)
        is_ramp_interface = (ramp_x_start - 1.0 <= v1.x <= ramp_x_end + 1.0) and (abs(v1.x - v2.x) < 1e-3)

        if is_at_top and not is_at_neck_stop and not is_ramp_interface:
            top_outer_edges.append(edge)

    if top_outer_edges:
        try:
            body_veneer_solid = body_veneer_solid.makeFillet(top_edge_radius, top_outer_edges)
            App.Console.PrintMessage("Filleted outer top veneer edges successfully.\n")
        except Exception as top_f_err:
            App.Console.PrintWarning(f"Top edge filleting bypassed: {str(top_f_err)}\n")

    # 4. FUSE WITH FINGER RAMP
    if 'ramp_solid' in locals() and ramp_solid:
        try:
            ramp_copy = ramp_solid.copy()
            ramp_z_bottom_local = ramp_copy.BoundBox.ZMin
            
            # 4a. Fillet ramp vertical edges
            ramp_vertical_edges = []
            for r_edge in ramp_copy.Edges:
                rv1, rv2 = r_edge.Vertexes[0].Point, r_edge.Vertexes[1].Point
                if (abs(rv1.x - rv2.x) < 1e-3) and (abs(rv1.y - rv2.y) < 1e-3) and (abs(rv1.z - rv2.z) > 1e-3):
                    ramp_vertical_edges.append(r_edge)

            if ramp_vertical_edges:
                try:
                    ramp_copy = ramp_copy.makeFillet(outer_corner_radius, ramp_vertical_edges)
                except Exception:
                    pass

            # 4b. Fillet ramp top edges
            ramp_top_edges = []
            for r_edge in ramp_copy.Edges:
                rv1, rv2 = r_edge.Vertexes[0].Point, r_edge.Vertexes[1].Point
                # Any edge where both vertices sit comfortably above the bottom plane belongs to the top boundary
                if (rv1.z > ramp_z_bottom_local + 0.5) and (rv2.z > ramp_z_bottom_local + 0.5):
                    # Ensure we don't accidentally grab a vertical edge
                    is_vert = (abs(rv1.x - rv2.x) < 1e-3) and (abs(rv1.y - rv2.y) < 1e-3) and (abs(rv1.z - rv2.z) > 1e-3)
                    if not is_vert:
                        ramp_top_edges.append(r_edge)

            if ramp_top_edges:
                try:
                    # Apply the same matching top_edge_radius (0.6mm) to the finger ramp top
                    ramp_copy = ramp_copy.makeFillet(top_edge_radius, ramp_top_edges)
                    App.Console.PrintMessage("Filleted top edges of FingerRamp successfully.\n")
                except Exception as rt_err:
                    App.Console.PrintWarning(f"Ramp top edge filleting bypassed: {str(rt_err)}\n")

            # 4c. Perform solid union
            body_veneer_solid = body_veneer_solid.fuse(ramp_copy)
            
            if 'ramp_feature' in locals() and ramp_feature:
                ramp_feature.ViewObject.Visibility = False
                
            App.Console.PrintMessage("Successfully fused pre-filleted FingerRamp and CoreBodyVeneer.\n")
        except Exception as embed_err:
            App.Console.PrintWarning(f"Finger ramp fusion bypassed: {str(embed_err)}\n")

    # 5. FILLET JOIN SEAM AT INTERSECTION
    seam_edges = []
    for edge in body_veneer_solid.Edges:
        v1, v2 = edge.Vertexes[0].Point, edge.Vertexes[1].Point
        is_vertical = (abs(v1.x - v2.x) < 1e-3) and (abs(v1.y - v2.y) < 1e-3) and (abs(v1.z - v2.z) > 1e-3)
        
        if is_vertical and (v_body_x_start + 5.0 < v1.x < neck_stop_x - 5.0):
            seam_edges.append(edge)

    if seam_edges:
        try:
            body_veneer_solid = body_veneer_solid.makeFillet(seam_fillet_radius, seam_edges)
            App.Console.PrintMessage("Filleted transition seam successfully.\n")
        except Exception as seam_err:
            App.Console.PrintWarning(f"Seam filleting bypassed gracefully: {str(seam_err)}\n")

    # 6. CUT TRUSS ROD ACCESS SLOT
    if cf_wrap_thickness == 0.0:
        truss_veneer_cutter = Part.makeBox(
            30.0, 10.0, 20.0, 
            App.Vector(neck_stop_x - 30.0, center_y - 10.0 / 2.0, z_veneer_bottom - 5.0)
        )
        body_veneer_solid = body_veneer_solid.cut(truss_veneer_cutter)
        App.Console.PrintMessage("Cut Truss Rod Access Slot out of CoreBodyVeneer.\n")

    # 7. REFINE SHAPE: Merge coplanar bottom faces into a single face
    try:
        body_veneer_solid = body_veneer_solid.removeSplitter()
        App.Console.PrintMessage("Refined CoreBodyVeneer topology: merged coplanar faces.\n")
    except Exception as ref_err:
        App.Console.PrintWarning(f"Shape refinement bypassed: {str(ref_err)}\n")

    # 8. ISOLATE STANDALONE FEATURE
    standalone_body_veneer = body_veneer_solid.copy()

    core_veneer_feature = doc.addObject("Part::Feature", "CoreBodyVeneer")
    core_veneer_feature.Shape = standalone_body_veneer
    core_veneer_feature.ViewObject.ShapeColor = (0.20, 0.12, 0.08)  # Ebony / dark wood preview
    core_veneer_feature.Label = "CoreBodyVeneer"
    App.Console.PrintMessage("Successfully generated clean, unified CoreBodyVeneer object with full edge filleting.\n")

except Exception as body_v_err:
    App.Console.PrintError(f"Failed to generate core body veneer: {str(body_v_err)}\n")

doc.recompute()
gc.collect()
